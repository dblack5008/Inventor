' GROUPED MOUNTING HARDWARE (Inventor 2027, assembly-level EXTERNAL iLogic rule)
' Uses native part Hole features: one feature and one point sketch per unique hole specification.
' Operates on the part file referenced by the selected plate occurrence. DOES NOT move components.
' Select a planar plate face, then select circular hole rims on the mounted components.
' The plate can be a top-level part or a part inside a subassembly. Holes are cut in that part file.
' Hardware is placed in the open assembly.
' Click a hole rim, or drag a box over hole edges. Click FINISH SELECTION & REVIEW to finish (no ESC dependence). Clicked rims stay cyan while selecting.
' Review groups, then commit. Inward direction is VERIFIED by checking that solid
' material is removed at EVERY selected hole center (and flipped if necessary).
' Native progress bars report both review/validation and hole generation.
' Countersink: angle dropdown defaults to 82 degrees (100 available); entered
' seat diameter and angle are reapplied AFTER clearance association and
' VERIFIED again after part recompute. No silent reversion to table defaults.
' Supports native clearance holes, tapped holes, custom holes, and none/counterbore/countersink/spotface seats.
' Group identity is the size, thread, seat, and clearance specification. The group name is not part of it.
' A name change updates the existing feature. A specification change does not, and the rule explains why before cutting.
' Each identity field is its own attribute (Inventor string attributes hold 255 characters). The set is copied with the feature.
' After the holes succeed, the rule can place washers from the hardware library.
' The nut side is either the hole rim you clicked or the plate face you selected first.
' A washer under the nut sits on that side. A washer under the screw sits on the other side.
' A nut sits on the nut side, outside the washer under the nut when that washer is placed.
' The first time a nut or screw is used, click the face that sits against the washer. That face is saved on the part.
' A flathead has no flat underside. Click its flat top. The shank is used to aim the tip into the hole.
' Before each screw file window, the rule shows the length under the head: rim-to-plate span, washers, and nut.
' Holes that need a different length get their own screw. The file window opens Hardware\<size>\Screws\<length>Lg.
' Placed hardware keeps the part file's own name in the assembly browser.
' The hole review can place hardware without cutting or changing the plate holes.
' A hole already in the plate is recognized. Hardware is placed on it, and that location is not cut again.
' Countersink, counterbore, and spotface holes use the review diameters. They are not linked to Clearance.xls.
' Sketch and feature naming are collision-resistant and non-fatal if Inventor rejects a rename.
' Default recommendations skip odd fastener numbers after #3.
' All numbered fasteners (#5/#7/#9/#11 included) remain available for manual selection.
' IMPORTANT: Diameter presets are editable initial suggestions, NOT queried from Inventor's
' local Clearance.xls. Always use the fastener/PEM manufacturer's installation requirements.
' This is a test-ready first version. First run on a COPY of an assembly and plate.
'
Sub Main()
    Dim app As Inventor.Application = ThisApplication
    Dim aDoc As Inventor.AssemblyDocument = TryCast(app.ActiveDocument, Inventor.AssemblyDocument)
    If aDoc Is Nothing Then
        System.Windows.Forms.MessageBox.Show("Open an .iam assembly before running this rule.", "Grouped Mounting Hardware")
        Exit Sub
    End If

    ' Inventor 2027: CommandManager.Pick may ignore ESC. Use event-based
    ' selection with a visible Cancel button instead, including for the plate.
    Dim plateSelector As New MGHInteractionSelector()
    Dim gotFace As Boolean = plateSelector.Run( _
        app, Inventor.SelectionFilterEnum.kPartFacePlanarFilter, _
        "Select Mounting Plate", _
        "Click the flat mounting face of the plate. The rule will automatically continue.", True)
    If Not gotFace OrElse plateSelector.Picked.Count = 0 Then Exit Sub
    Dim faceObj As Object = plateSelector.Picked(0)
    Dim plateFaceProxy As Inventor.FaceProxy = TryCast(faceObj, Inventor.FaceProxy)
    If plateFaceProxy Is Nothing Then
        System.Windows.Forms.MessageBox.Show("Select a planar face belonging to an actual plate part occurrence.")
        Exit Sub
    End If

    Dim plateOcc As Inventor.ComponentOccurrence = plateFaceProxy.ContainingOccurrence
    If plateOcc Is Nothing Then
        System.Windows.Forms.MessageBox.Show("Select a planar face belonging to an actual plate part occurrence.")
        Exit Sub
    End If
    Dim plateDef As Inventor.PartComponentDefinition = TryCast(plateOcc.Definition, Inventor.PartComponentDefinition)
    If plateDef Is Nothing Then
        System.Windows.Forms.MessageBox.Show("The selected plate is not an editable .ipt part.")
        Exit Sub
    End If
    Dim plateDoc As Inventor.PartDocument = TryCast(plateDef.Document, Inventor.PartDocument)
    If plateDoc Is Nothing OrElse Not plateDoc.IsModifiable Then
        System.Windows.Forms.MessageBox.Show("The plate .ipt is not modifiable. Check read-only, library, and active-edit state.")
        Exit Sub
    End If

    Dim plateNativeFace As Inventor.Face = plateFaceProxy.NativeObject
    Dim platePlane As Inventor.Plane = TryCast(plateNativeFace.Geometry, Inventor.Plane)
    Dim plateAssemblyPlane As Inventor.Plane = TryCast(plateFaceProxy.Geometry, Inventor.Plane)
    If platePlane Is Nothing OrElse plateAssemblyPlane Is Nothing Then
        System.Windows.Forms.MessageBox.Show("The selected plate face must be planar.")
        Exit Sub
    End If

    ' A face picked in this assembly belongs to a proxy whose transform is already
    ' expressed here, including a part that sits inside a subassembly. If that
    ' transform does not put the part face on the face that was clicked, the
    ' occurrence only knows its position inside its parent, so multiply each
    ' level from the part out to this assembly.
    Dim plateToAssembly As Inventor.Matrix = MGHPartToAssembly(plateOcc, plateNativeFace, plateFaceProxy)
    If plateToAssembly Is Nothing Then
        System.Windows.Forms.MessageBox.Show( _
            "The plate's position in this assembly could not be read, so no holes were created.", _
            "Grouped Mounting Hardware")
        Exit Sub
    End If
    Dim invertPlate As Inventor.Matrix = plateToAssembly.Copy()
    invertPlate.Invert()
    Dim plateOutX As Double = plateAssemblyPlane.Normal.X
    Dim plateOutY As Double = plateAssemblyPlane.Normal.Y
    Dim plateOutZ As Double = plateAssemblyPlane.Normal.Z
    Try
        Dim plateOut As Inventor.UnitVector = MGHFaceOutward(plateFaceProxy, plateFaceProxy.SurfaceBody, app)
        plateOutX = plateOut.X : plateOutY = plateOut.Y : plateOutZ = plateOut.Z
    Catch
    End Try

    Dim holeSelector As New MGHInteractionSelector()
    Dim gotHoles As Boolean = holeSelector.Run( _
        app, Inventor.SelectionFilterEnum.kPartEdgeCircularFilter, _
        "Select Component Mounting Holes", _
        "Click each circular hole rim, or drag a box over the hole edges. When finished, click FINISH SELECTION & REVIEW in the floating palette.", False)
    If Not gotHoles Then Exit Sub

    Dim selected As New System.Collections.Generic.List(Of MountPoint)()
    Dim excluded As New System.Collections.Generic.List(Of String)()
    For Each item As Object In holeSelector.Picked
        Try
            Dim e As Inventor.EdgeProxy = TryCast(item, Inventor.EdgeProxy)
            If e Is Nothing Then Throw New System.Exception("Not an assembly circular edge.")
            Dim circ As Inventor.Circle = TryCast(e.Geometry, Inventor.Circle)
            If circ Is Nothing Then Throw New System.Exception("Only full circular edges are supported; select the complete hole rim.")
            Dim measuredCenter As Inventor.Point = circ.Center
            Dim measuredAxis As Inventor.UnitVector = circ.Normal
            Dim radiusCm As Double = circ.Radius
            Dim sourceOccurrence As Inventor.ComponentOccurrence = e.ContainingOccurrence
            Dim sourceName As String = sourceOccurrence.Name
            If sourceOccurrence.Definition.Document.FullFileName = plateDoc.FullFileName Then
                Throw New System.Exception("Source is a face/edge on the plate itself.")
            End If
            If radiusCm <= 0.0 Then Throw New System.Exception("Invalid radius.")
            If System.Math.Abs(measuredAxis.DotProduct(plateAssemblyPlane.Normal)) < 0.9990 Then
                Throw New System.Exception("Hole axis is not perpendicular to the plate (tolerance about 2.6 deg).")
            End If

            ' Geometry of proxies is in assembly space. Transform into *plate-part* space;
            ' never manipulate assembly component position or use camera/view orientation.
            Dim inPlate As Inventor.Point = measuredCenter.Copy()
            inPlate.TransformBy(invertPlate)
            Dim onPlane As Inventor.Point = ProjectToPlane(inPlate, platePlane, app)
            Dim nearest As Inventor.Point = plateNativeFace.GetClosestPointTo(onPlane)
            Dim distanceToFace As Double = nearest.DistanceTo(onPlane)
            Dim existingOpening As Boolean = False
            If distanceToFace > 0.003 Then ' 0.03 mm, Inventor internal cm
                ' A center that falls in a hole already in the plate is still a valid
                ' hardware location. Only a center outside the plate outline is rejected.
                Dim rimGap As Double = MGHNearestCircularCenterGap(plateNativeFace, onPlane)
                If Not MGHAcceptExistingOpening(distanceToFace, rimGap) Then
                    Throw New System.Exception("Projected center is outside the plate face.")
                End If
                existingOpening = True
            End If
            Dim alreadySelected As Boolean = False
            For Each prior As MountPoint In selected
                If prior.Center.DistanceTo(onPlane) < 0.005 Then ' 0.05 mm
                    alreadySelected = True
                    Exit For
                End If
            Next
            If alreadySelected Then Throw New System.Exception("That hole center is already selected.")

            Dim rec As New MountPoint()
            rec.Center = onPlane
            rec.SourceDiameterIn = (radiusCm * 2.0 / 2.54)
            rec.SourceName = sourceName
            Dim rimRec As New MGHComponentRim()
            rimRec.Component = sourceOccurrence
            rimRec.SelectedEdge = e
            rimRec.CenterX = measuredCenter.X
            rimRec.CenterY = measuredCenter.Y
            rimRec.CenterZ = measuredCenter.Z
            rimRec.AxisX = measuredAxis.X
            rimRec.AxisY = measuredAxis.Y
            rimRec.AxisZ = measuredAxis.Z
            rimRec.Radius = radiusCm
            rec.Rim = rimRec
            rec.ExistingOpening = existingOpening
            selected.Add(rec)
        Catch ex As System.Exception
            excluded.Add("Skipped selection " & (selected.Count + excluded.Count + 1).ToString() & ": " & ex.Message)
        End Try
    Next

    If selected.Count = 0 Then
        System.Windows.Forms.MessageBox.Show("No usable component holes selected." & _
            If(excluded.Count > 0, vbCrLf & String.Join(vbCrLf, excluded.ToArray()), ""), "No changes")
        Exit Sub
    End If

    Dim buckets As New System.Collections.Generic.SortedDictionary(Of String, InputBucket)(System.StringComparer.Ordinal)
    For Each m As MountPoint In selected
        Dim key As String = m.SourceDiameterIn.ToString("0.000", System.Globalization.CultureInfo.InvariantCulture)
        If Not buckets.ContainsKey(key) Then
            Dim b As New InputBucket()
            b.SourceKey = key
            b.Screw = GuessFastener(m.SourceDiameterIn)
            b.Fit = "Normal"
            b.Mode = "Clearance"
            b.Seat = "None"
            b.ThreadType = "ANSI Unified Screw Threads"
            b.ThreadDesignation = MGHDefaultThread(b.Screw)
            b.ThreadClass = "2B"
            b.ClearanceStandard = "Ansi Unified Screw Threads"
            b.ClearanceFamily = "Flat Head Machine Screw (100)"
            b.DiameterIn = PresetDiameter(b.Screw, b.Fit)
            b.GroupLabel = "Hole " & b.Screw & " - Normal"
            buckets.Add(key, b)
        End If
        buckets(key).Centers.Add(m.Center)
        buckets(key).Rims.Add(m.Rim)
        buckets(key).ExistingOpening.Add(m.ExistingOpening)
    Next

    ' Restore saved group names before the review grid is built. The grid's
    ' suggested name is not the feature identity; overwriting a stored name
    ' on every run would discard a rename.
    Dim planeID As String = StablePlaneKey(platePlane)
    Try
        MGHApplyStoredLabels(buckets, plateDef, planeID)
    Catch ex As System.Exception
        System.Windows.Forms.MessageBox.Show("Existing grouped holes could not be read:" & vbCrLf & ex.Message, "Grouped Mounting Hardware")
        Exit Sub
    End Try

    Dim review As New HoleReviewForm(buckets)
    review.Text = "Grouped Mounting Hardware - " & plateDoc.DisplayName
    Dim outcome As System.Windows.Forms.DialogResult = review.ShowDialog()
    If outcome <> System.Windows.Forms.DialogResult.OK Then Exit Sub

    ' Generating holes can take a while when many hole positions are checked.
    ' Create a SECOND, clearly labeled progress bar *before* the checks start.
    Dim reviewProgress As Inventor.ProgressBar = Nothing
    Dim reviewOperation As String = "Preparing review"
    Dim desiredGroups As New System.Collections.Generic.SortedDictionary(Of String, OutputGroup)(System.StringComparer.Ordinal)
    Try
        Dim reviewSteps As Integer = 4 + buckets.Count + selected.Count
        reviewProgress = app.CreateProgressBar(False, reviewSteps, "Grouped Mounting Hardware - Reviewing / Validating")
        MGHProgressTick(reviewProgress, app, "Collecting selected mounting-hole specifications")
        For Each b As InputBucket In buckets.Values
            reviewOperation = "Validating specification for source Ø" & b.SourceKey
            MGHProgressMessage(reviewProgress, app, reviewOperation)
            If String.IsNullOrWhiteSpace(b.GroupLabel) Then Throw New System.Exception("Group name is required for Ø" & b.SourceKey)
            If b.Mode <> "Threaded" AndAlso (b.DiameterIn <= 0.01 OrElse b.DiameterIn > 2.0) Then
                Throw New System.Exception("Invalid target Ø for source " & b.SourceKey)
            End If
            If b.Mode = "Clearance" Then
                If b.ClearanceStandard.Trim() = "" OrElse b.ClearanceFamily.Trim() = "" Then
                    Throw New System.Exception("Enter Inventor clearance standard and fastener family for " & b.GroupLabel)
                End If
            End If
            If b.Mode = "Threaded" Then
                If b.ThreadType.Trim() = "" OrElse b.ThreadDesignation.Trim() = "" OrElse b.ThreadClass.Trim() = "" Then
                    Throw New System.Exception("Threaded group '" & b.GroupLabel & "' needs a type, designation and internal class.")
                End If
            End If
            If b.Seat <> "None" Then
                If b.SeatDiameterIn <= 0 Then Throw New System.Exception("Enter a seat diameter for " & b.GroupLabel)
                If b.Seat = "Countersink" Then
                    If b.SeatAngleDeg <= 0 OrElse b.SeatAngleDeg >= 180 Then Throw New System.Exception("Countersink angle must be between 0 and 180 degrees.")
                Else
                    If b.SeatDepthIn <= 0 Then Throw New System.Exception("Enter a positive seat depth for " & b.GroupLabel)
                End If
                If b.Mode <> "Threaded" AndAlso b.SeatDiameterIn <= b.DiameterIn Then
                    Throw New System.Exception("Seat Ø must exceed the hole Ø for " & b.GroupLabel)
                End If
            End If
            MGHRequireStorable("Group name", b.GroupLabel)
            MGHRequireStorable("Fastener", b.Screw)
            MGHRequireStorable("Fit", b.Fit)
            MGHRequireStorable("Hole type", b.Mode)
            MGHRequireStorable("Seat", b.Seat)
            MGHRequireStorable("Thread type", b.ThreadType)
            MGHRequireStorable("Thread designation", b.ThreadDesignation)
            MGHRequireStorable("Thread class", b.ThreadClass)
            MGHRequireStorable("Clearance standard", b.ClearanceStandard)
            MGHRequireStorable("Clearance family", b.ClearanceFamily)
            Dim diameterText As String = b.DiameterIn.ToString("0.000000", System.Globalization.CultureInfo.InvariantCulture)
            Dim key As String = MGHSpecKeyFromBucket(planeID, b)
            If desiredGroups.ContainsKey(key) AndAlso _
               Not String.Equals(desiredGroups(key).Label, b.GroupLabel.Trim(), System.StringComparison.OrdinalIgnoreCase) Then
                Throw New System.Exception("Two rows use the same hole specification but different group names ('" & _
                    desiredGroups(key).Label & "' and '" & b.GroupLabel.Trim() & "'). " & _
                    "The name is not part of the feature identity. Use one name, or change the specification.")
            End If
            If Not desiredGroups.ContainsKey(key) Then
                Dim g As New OutputGroup()
                g.Key = key
                g.LegacyKey = MGHSizeKey(planeID, b.Screw, b.Fit, diameterText)
                g.PlaneId = planeID
                g.Label = b.GroupLabel.Trim() : g.DiameterIn = b.DiameterIn
                g.Screw = b.Screw : g.Fit = b.Fit : g.Mode = b.Mode : g.Seat = b.Seat
                g.SeatDiameterIn = b.SeatDiameterIn : g.SeatDepthIn = b.SeatDepthIn : g.SeatAngleDeg = b.SeatAngleDeg
                g.ThreadType = b.ThreadType : g.ThreadDesignation = b.ThreadDesignation : g.ThreadClass = b.ThreadClass
                g.ClearanceStandard = b.ClearanceStandard : g.ClearanceFamily = b.ClearanceFamily
                desiredGroups.Add(key, g)
            End If
            Dim centerIndex As Integer
            For centerIndex = 0 To b.Centers.Count - 1
                Dim p As Inventor.Point = b.Centers(centerIndex)
                desiredGroups(key).Centers.Add(p)
                Dim opening As Boolean = centerIndex < b.ExistingOpening.Count AndAlso b.ExistingOpening(centerIndex)
                If opening Then
                    desiredGroups(key).OpeningCenters.Add(p)
                Else
                    desiredGroups(key).CentersToCut.Add(p)
                End If
            Next
            For Each rim As MGHComponentRim In b.Rims
                desiredGroups(key).Rims.Add(rim)
            Next
            MGHProgressTick(reviewProgress, app, "Grouped source Ø" & b.SourceKey & " — " & b.Centers.Count.ToString() & " positions")
        Next

        ' Hardware-only leaves existing holes alone, including holes this rule did not cut.
        If Not review.SkipHoleCreation Then
        reviewOperation = "Comparing specifications with existing grouped holes"
        MGHProgressMessage(reviewProgress, app, reviewOperation)
        MGHDescribeExistingGroups(plateDef, desiredGroups)

        ' Test full seat envelope (NOT only pilot/core hole diameter).
        reviewOperation = "Checking selected face boundaries and hole/seat interference"
        MGHProgressTick(reviewProgress, app, reviewOperation)
        Dim allLocations As New System.Collections.Generic.List(Of Inventor.Point)()
        Dim allRadii As New System.Collections.Generic.List(Of Double)()
        For Each g As OutputGroup In desiredGroups.Values
            Dim effectiveDiameter As Double = g.DiameterIn
            If g.Mode = "Threaded" Then
                ' Use the nominal major diameter from the actual thread designation
                ' as the conservative envelope, not the minor/tap-drill diameter.
                effectiveDiameter = MGHThreadNominalFromDesignation(g.ThreadDesignation)
                If effectiveDiameter <= 0 Then effectiveDiameter = MGHThreadNominalDiameter(g.Screw)
                If effectiveDiameter <= 0 Then
                    Dim designation As String = g.ThreadDesignation.Trim().ToUpperInvariant()
                    If designation.StartsWith("M") Then
                        Dim cap As String = designation.Substring(1).Split("X"c)(0)
                        Dim nominalMm As Double=0
                        If Double.TryParse(cap,System.Globalization.NumberStyles.Float,System.Globalization.CultureInfo.InvariantCulture,nominalMm) Then
                            effectiveDiameter=nominalMm/25.4
                        End If
                    End If
                End If
                If effectiveDiameter <= 0 Then
                    Throw New System.Exception("Cannot validate the pilot hole diameter for custom thread " & g.ThreadDesignation & _
                        ". Choose a nominal screw size or use an M# thread designation.")
                End If
            End If
            If g.Seat <> "None" Then effectiveDiameter = System.Math.Max(effectiveDiameter, g.SeatDiameterIn)
            Dim radius As Double = effectiveDiameter * 2.54 / 2.0
            For Each pos As Inventor.Point In g.Centers
                reviewOperation = "Checking " & g.Label & " — location " & (allLocations.Count + 1).ToString()
                MGHProgressMessage(reviewProgress, app, reviewOperation)
                For Each perimeter As Inventor.Edge In plateNativeFace.Edges
                    If MGHGroupUsesOpening(g, pos) AndAlso MGHEdgeCenteredOn(perimeter, pos, 0.08) Then Continue For
                    Dim onEdge As Inventor.Point = perimeter.GetClosestPointTo(pos)
                    If onEdge.DistanceTo(pos) + 0.0001 < radius Then
                        Throw New System.Exception("Hole/seat '" & g.Label & "' envelope would intersect plate-face boundary or opening.")
                    End If
                Next
                For j As Integer = 0 To allLocations.Count - 1
                    If pos.DistanceTo(allLocations(j)) + 0.0001 < radius + allRadii(j) Then
                        Throw New System.Exception("Two requested hole/seat envelopes overlap. Adjust sizes or locations before continuing.")
                    End If
                Next
                allLocations.Add(pos) : allRadii.Add(radius)
                MGHProgressTick(reviewProgress, app, "Checked " & allLocations.Count.ToString() & "/" & selected.Count.ToString() & " hole/seat envelopes")
            Next
        Next
        End If
        reviewOperation = "Finishing validation for " & desiredGroups.Count.ToString() & " groups"
        MGHProgressTick(reviewProgress, app, reviewOperation)
        MGHProgressTick(reviewProgress, app, "Validation finished")
    Catch ex As System.Exception
        System.Windows.Forms.MessageBox.Show("Review validation failed: " & reviewOperation & vbCrLf & ex.Message, "Grouped Mounting Hardware")
        Exit Sub
    Finally
        If reviewProgress IsNot Nothing Then
            Try
                reviewProgress.Close()
            Catch
            End Try
        End If
    End Try

    Dim cutsRequested As Integer = 0
    Dim openingsReused As Integer = 0
    For Each countedGroup As OutputGroup In desiredGroups.Values
        cutsRequested += countedGroup.CentersToCut.Count
        openingsReused += countedGroup.OpeningCenters.Count
    Next
    If review.SkipHoleCreation OrElse cutsRequested = 0 Then
        Dim hardwareOnlySummary As String = ""
        Try
            hardwareOnlySummary = MGHPlaceWashers(app, aDoc, desiredGroups, plateOcc, plateToAssembly, plateOutX, plateOutY, plateOutZ)
        Catch washerEx As System.Exception
            hardwareOnlySummary = "Hardware was not placed." & vbCrLf & washerEx.Message
        End Try
        Dim holeLead As String
        If review.SkipHoleCreation Then
            holeLead = "Holes were left unchanged on " & plateDoc.DisplayName & "."
        Else
            holeLead = "The plate already has a hole at each selected location (" & openingsReused.ToString() & "). Those holes were left unchanged on " & plateDoc.DisplayName & "."
        End If
        System.Windows.Forms.MessageBox.Show( _
            holeLead & vbCrLf & vbCrLf & _
            hardwareOnlySummary & vbCrLf & vbCrLf & _
            "Inspect the hardware clearances, then SAVE the assembly.", _
            "Grouped Mounting Hardware")
        Exit Sub
    End If

    Dim trans As Inventor.Transaction = Nothing
    Dim progress As Inventor.ProgressBar = Nothing
    Dim operationInfo As String = "Starting plate transaction"
    Try
        ' Every tick represents a REAL completed unit of work; no estimated clock times.
        ' Steps: begin, scan, (prepare + finish each group), each selected location,
        ' final recompute, commit.
        Dim progressSteps As Integer = 4 + 2 * desiredGroups.Count
        For Each gg As OutputGroup In desiredGroups.Values
            progressSteps += gg.Centers.Count
        Next
        progress = app.CreateProgressBar(False, progressSteps, "Grouped Mounting Hardware - Generating")
        progress.Message = "Opening transaction for " & plateDoc.DisplayName
        trans = app.TransactionManager.StartTransaction(plateDoc, "Generate Grouped Mounting Hardware")
        MGHProgressTick(progress, app, "Plate transaction started - checking existing groups")
        Dim holes As Inventor.HoleFeatures = plateDef.Features.HoleFeatures
        Dim featureIndex As MGHFeatureIndex = MGHLoadFeatureIndex(plateDef)
        Dim existing As New System.Collections.Generic.Dictionary(Of String, Inventor.HoleFeature)(System.StringComparer.Ordinal)
        Dim migrateLegacy As New System.Collections.Generic.Dictionary(Of String, Inventor.HoleFeature)(System.StringComparer.Ordinal)
        For Each g As OutputGroup In desiredGroups.Values
            If featureIndex.BySpec.ContainsKey(g.Key) Then
                existing.Add(g.Key, featureIndex.BySpec(g.Key))
            ElseIf g.Mode = "Clearance" AndAlso g.Seat = "None" AndAlso featureIndex.ByV15Size.ContainsKey(g.LegacyKey) Then
                ' V1.5 stored only screw, fit, diameter, and the display name.
                ' Upgrade that feature when the new request is still a plain clearance hole.
                existing.Add(g.Key, featureIndex.ByV15Size(g.LegacyKey))
                migrateLegacy.Add(g.Key, featureIndex.ByV15Size(g.LegacyKey))
            End If
        Next
        MGHProgressTick(progress, app, "Existing groups indexed - preparing " & desiredGroups.Count.ToString() & " size groups")

        ' Prepare every NEW sketch BEFORE cutting: subsequent cuts can change face topology.
        ' For each sketch, derive its +normal from its sketch coordinates and use
        ' SurfaceBody.IsPointInside to verify WHICH DIRECTION ENTERS THE SOLID.
        ' Do NOT assume kNegative is the right direction and do NOT use COM success
        ' as evidence a Hole feature removed material.
        Dim createdFeatures As New System.Collections.Generic.Dictionary(Of String, Inventor.HoleFeature)(System.StringComparer.Ordinal)
        Dim newSketches As New System.Collections.Generic.Dictionary(Of String, Inventor.PlanarSketch)(System.StringComparer.Ordinal)
        Dim newCenters As New System.Collections.Generic.Dictionary(Of String, Inventor.ObjectCollection)(System.StringComparer.Ordinal)
        Dim inwardDirections As New System.Collections.Generic.Dictionary(Of String, Inventor.PartFeatureExtentDirectionEnum)(System.StringComparer.Ordinal)
        Dim interiorTestPoints As New System.Collections.Generic.Dictionary(Of String, System.Collections.Generic.List(Of Inventor.Point))(System.StringComparer.Ordinal)
        Dim flippedGroups As Integer = 0
        Dim renamedGroups As Integer = 0
        Dim namingWarnings As New System.Collections.Generic.List(Of String)()
        Dim skippedDuplicates As Integer = 0
        Dim newPoints As Integer = 0
        Dim updatedGroups As Integer = 0
        Dim newGroups As Integer = 0
        Dim plateBody As Inventor.SurfaceBody = plateNativeFace.SurfaceBody
        Dim preparationIndex As Integer = 0
        For Each g As OutputGroup In desiredGroups.Values
            preparationIndex += 1
            operationInfo = "Preparing group " & preparationIndex.ToString() & "/" & desiredGroups.Count.ToString() & ": " & g.Label
            MGHProgressMessage(progress, app, operationInfo)
            If existing.ContainsKey(g.Key) AndAlso g.CentersToCut.Count = 0 Then
                ' Every selected center already opens through the plate. Leave the feature alone.
            ElseIf existing.ContainsKey(g.Key) Then
                Dim feat As Inventor.HoleFeature = existing(g.Key)
                If g.Mode = "Threaded" Then
                    If Not feat.Tapped Then Throw New System.Exception("Existing group should be threaded but is not: " & feat.Name)
                    Dim storedTap As Inventor.HoleTapInfo = TryCast(feat.TapInfo, Inventor.HoleTapInfo)
                    If storedTap Is Nothing OrElse Not String.Equals(storedTap.ThreadDesignation, g.ThreadDesignation, System.StringComparison.OrdinalIgnoreCase) Then
                        Throw New System.Exception("Existing group thread designation differs: " & feat.Name)
                    End If
                ElseIf feat.HoleDiameter IsNot Nothing Then
                    If Not (g.Mode = "Clearance" AndAlso feat.IsClearanceHole) AndAlso _
                       System.Math.Abs(feat.HoleDiameter.Value - g.DiameterIn * 2.54) > 0.0002 Then
                        Throw New System.Exception("Existing group diameter differs: " & feat.Name & ". Check the feature and specifications.")
                    End If
                End If
                ' Only a clearance-linked countersink needs its seat written back. A plain
                ' countersink already has the review diameters, and rewriting it recomputes.
                If g.Seat = "Countersink" AndAlso feat.IsClearanceHole Then MGHEnforceCountersink(feat, g)
                MGHCheckExistingSeat(feat, g)
                Dim pd As Inventor.SketchHolePlacementDefinition = TryCast(feat.PlacementDefinition, Inventor.SketchHolePlacementDefinition)
                If pd Is Nothing Then Throw New System.Exception("Existing matching feature is no longer sketch-based: " & feat.Name)
                Dim existingSketch As Inventor.PlanarSketch = feat.Sketch
                Dim pendingCenters As New System.Collections.Generic.List(Of Inventor.Point)()
                For Each p As Inventor.Point In g.CentersToCut
                    Dim p2 As Inventor.Point2d = existingSketch.ModelToSketchSpace(p)
                    Dim found As Boolean = False
                    For Each sp As Inventor.SketchPoint In pd.HoleCenterPoints
                        If sp.Geometry.DistanceTo(p2) < 0.005 Then
                            found = True
                            Exit For
                        End If
                    Next
                    If Not found Then pendingCenters.Add(p)
                Next
                If pendingCenters.Count > 0 Then
                    operationInfo = "Determining plate interior for existing group: " & g.Label
                    inwardDirections.Add(g.Key, DetermineInwardDirection(existingSketch, plateBody, pendingCenters, app))
                    interiorTestPoints.Add(g.Key, MGHFindInteriorSamples(existingSketch, plateBody, pendingCenters, app))
                Else
                    ' Selected centers belonging to a previous outward-facing feature
                    ' may still have solid material beneath them. Test each center:
                    ' some centers might already be drilled and should be ignored.
                    Dim repairCenters As New System.Collections.Generic.List(Of Inventor.Point)()
                    For Each center As Inventor.Point In g.CentersToCut
                        Try
                            Dim one As New System.Collections.Generic.List(Of Inventor.Point)()
                            one.Add(center)
                            MGHFindInteriorSamples(existingSketch, plateBody, one, app)
                            repairCenters.Add(center)
                        Catch
                            ' This point is already open / has no material to cut.
                        End Try
                    Next
                    If repairCenters.Count > 0 Then
                        inwardDirections.Add(g.Key, DetermineInwardDirection(existingSketch, plateBody, repairCenters, app))
                        interiorTestPoints.Add(g.Key, MGHFindInteriorSamples(existingSketch, plateBody, repairCenters, app))
                    End If
                End If
            ElseIf g.CentersToCut.Count > 0 Then
                operationInfo = "Creating sketch for group: " & g.Label
                Dim sk As Inventor.PlanarSketch = plateDef.Sketches.Add(plateNativeFace, False)
                newSketches.Add(g.Key, sk)
                newCenters.Add(g.Key, app.TransientObjects.CreateObjectCollection())
                ' Never rename in this preparation loop. On some assemblies
                ' PlanarSketch.Name raises E_FAIL (e.g. name collision).
                operationInfo = "Determining plate interior for new group: " & g.Label
                inwardDirections.Add(g.Key, DetermineInwardDirection(sk, plateBody, g.CentersToCut, app))
                interiorTestPoints.Add(g.Key, MGHFindInteriorSamples(sk, plateBody, g.CentersToCut, app))
            End If
            MGHProgressTick(progress, app, "Prepared group " & preparationIndex.ToString() & "/" & desiredGroups.Count.ToString() & ": " & g.Label)
        Next

        ' Each new specification uses ONE sketch with all its center points,
        ' feeding ONE native part Hole feature.
        Dim generationIndex As Integer = 0
        For Each g As OutputGroup In desiredGroups.Values
            generationIndex += 1
            If existing.ContainsKey(g.Key) OrElse Not newSketches.ContainsKey(g.Key) Then Continue For
            operationInfo = "Building new group " & generationIndex.ToString() & "/" & desiredGroups.Count.ToString() & ": " & g.Label
            MGHProgressMessage(progress, app, operationInfo)
            Dim sk As Inventor.PlanarSketch = newSketches(g.Key)
            Dim pts As Inventor.ObjectCollection = newCenters(g.Key)
            Dim addedInGroup As Integer = 0
            For Each p As Inventor.Point In g.CentersToCut
                Dim p2 As Inventor.Point2d = sk.ModelToSketchSpace(p)
                Dim sp As Inventor.SketchPoint = sk.SketchPoints.Add(p2, True)
                sk.GeometricConstraints.AddGround(sp)
                pts.Add(sp)
                newPoints += 1
                addedInGroup += 1
                MGHProgressTick(progress, app, "Group " & generationIndex.ToString() & "/" & desiredGroups.Count.ToString() & _
                    ": " & g.Label & " - point " & addedInGroup.ToString() & "/" & g.CentersToCut.Count.ToString())
            Next
            operationInfo = "Drilling " & g.Label
            MGHProgressMessage(progress, app, operationInfo)
            Dim place As Inventor.SketchHolePlacementDefinition = holes.CreateSketchPlacementDefinition(pts)
            Dim h As Inventor.HoleFeature = MGHCreateGroupedFeature(holes, place, g, inwardDirections(g.Key))
            If h Is Nothing Then Throw New System.Exception("Inventor returned no Hole feature for " & g.Label)
            createdFeatures.Add(g.Key, h)
            ' Cut direction is checked once, after every new feature exists, so a
            ' countersink group does not recompute the part by itself.
            operationInfo = "Recording group identity: " & g.Label
            MGHPersistIdentity(h, g, holes, plateDef, sk, namingWarnings)
            newGroups += 1
            MGHProgressTick(progress, app, "New group " & generationIndex.ToString() & "/" & desiredGroups.Count.ToString() & " completed: " & g.Label)
        Next

        ' Extend existing matching groups, and ensure their Through All direction
        ' points INTO the plate at the newly requested hole location.
        generationIndex = 0
        For Each g As OutputGroup In desiredGroups.Values
            generationIndex += 1
            If Not existing.ContainsKey(g.Key) OrElse g.CentersToCut.Count = 0 Then Continue For
            operationInfo = "Checking existing group " & generationIndex.ToString() & "/" & desiredGroups.Count.ToString() & ": " & g.Label
            MGHProgressMessage(progress, app, operationInfo)
            Dim h As Inventor.HoleFeature = existing(g.Key)
            Dim ownedSketch As Inventor.PlanarSketch = Nothing
            Try
                ownedSketch = h.Sketch
            Catch
            End Try
            operationInfo = "Recording group identity: " & g.Label
            If MGHPersistIdentity(h, g, holes, plateDef, ownedSketch, namingWarnings) Then renamedGroups += 1
            Dim placement As Inventor.SketchHolePlacementDefinition = CType(h.PlacementDefinition, Inventor.SketchHolePlacementDefinition)
            Dim sk As Inventor.PlanarSketch = h.Sketch
            Dim allPts As Inventor.ObjectCollection = app.TransientObjects.CreateObjectCollection()
            For Each p As Inventor.SketchPoint In placement.HoleCenterPoints
                allPts.Add(p)
            Next
            Dim changed As Boolean = False
            Dim checkedInGroup As Integer = 0
            For Each p As Inventor.Point In g.CentersToCut
                checkedInGroup += 1
                MGHProgressTick(progress, app, "Group " & generationIndex.ToString() & "/" & desiredGroups.Count.ToString() & _
                    ": " & g.Label & " - checking point " & checkedInGroup.ToString() & "/" & g.CentersToCut.Count.ToString())
                Dim p2 As Inventor.Point2d = sk.ModelToSketchSpace(p)
                Dim duplicate As Boolean = False
                For Each existingPoint As Inventor.SketchPoint In placement.HoleCenterPoints
                    If existingPoint.Geometry.DistanceTo(p2) < 0.005 Then
                        duplicate = True
                        Exit For
                    End If
                Next
                If duplicate Then
                    skippedDuplicates += 1
                    Continue For
                End If
                Dim newSp As Inventor.SketchPoint = sk.SketchPoints.Add(p2, True)
                sk.GeometricConstraints.AddGround(newSp)
                allPts.Add(newSp)
                changed = True
                newPoints += 1
            Next
            If changed Then
                placement.HoleCenterPoints = allPts
            End If
            ' If previously generated holes point into empty space, retry the group
            ' even when no new centers were added.
            If changed OrElse interiorTestPoints.ContainsKey(g.Key) Then
                operationInfo = "Verifying / repairing existing group: " & g.Label
                MGHProgressMessage(progress, app, operationInfo)
                h.SetThroughAllExtent(inwardDirections(g.Key))
                If migrateLegacy.ContainsKey(g.Key) Then
                    operationInfo = "Upgrading legacy clearance association: " & g.Label
                    MGHProgressMessage(progress, app, operationInfo)
                    MGHApplyClearanceInfo(holes, h, g)
                End If
                updatedGroups += 1
            End If
            If migrateLegacy.ContainsKey(g.Key) Then
                If Not h.IsClearanceHole Then
                    MGHApplyClearanceInfo(holes, h, g)
                End If
            End If
            MGHProgressTick(progress, app, "Existing group " & generationIndex.ToString() & "/" & desiredGroups.Count.ToString() & " checked: " & g.Label)
        Next

        operationInfo = "Final validation: recomputing the mounting plate"
        MGHProgressMessage(progress, app, operationInfo)
        If Not plateDoc.Update2(False) Then
            Throw New System.Exception("Inventor reports one or more part features failed to recompute. " & _
                "The transaction will be aborted; inspect the model/feature geometry.")
        End If
        operationInfo = "Checking that each new hole removed material"
        MGHProgressMessage(progress, app, operationInfo)
        flippedGroups += MGHConfirmCutDirections(plateDoc, plateDef, desiredGroups, existing, createdFeatures, interiorTestPoints, app, progress)
        ' Recompute can cause native clearance tables to restore countersink
        ' dimensions. Reject the group if the saved model differs from user input.
        operationInfo = "Confirming countersink diameters and included angles after recompute"
        MGHProgressMessage(progress, app, operationInfo)
        For Each requested As OutputGroup In desiredGroups.Values
            If requested.Seat <> "Countersink" Then Continue For
            Dim checkFeat As Inventor.HoleFeature = Nothing
            If createdFeatures.ContainsKey(requested.Key) Then
                checkFeat = createdFeatures(requested.Key)
            ElseIf existing.ContainsKey(requested.Key) AndAlso requested.CentersToCut.Count > 0 Then
                checkFeat = existing(requested.Key)
            End If
            If checkFeat IsNot Nothing Then MGHAssertCountersink(checkFeat, requested)
        Next
        MGHProgressTick(progress, app, "Final model recompute and countersink dimensions passed")
        operationInfo = "Committing the plate transaction"
        MGHProgressMessage(progress, app, operationInfo)
        trans.End()
        trans = Nothing
        MGHProgressTick(progress, app, "Finished - plate transaction committed")
        If progress IsNot Nothing Then
            progress.Close()
            progress = Nothing
        End If
        Dim washerSummary As String = ""
        Try
            washerSummary = MGHPlaceWashers(app, aDoc, desiredGroups, plateOcc, plateToAssembly, plateOutX, plateOutY, plateOutZ)
        Catch washerEx As System.Exception
            washerSummary = "Hardware was not placed." & vbCrLf & washerEx.Message
        End Try
        System.Windows.Forms.MessageBox.Show( _
            "Finished editing " & plateDoc.DisplayName & vbCrLf & _
            "New groups/features: " & newGroups.ToString() & vbCrLf & _
            "Existing groups extended/repaired: " & updatedGroups.ToString() & vbCrLf & _
            "Group names updated: " & renamedGroups.ToString() & vbCrLf & _
            "Groups whose cut direction was reversed: " & flippedGroups.ToString() & vbCrLf & _
            "New hole centers: " & newPoints.ToString() & vbCrLf & _
            "Duplicate centers skipped: " & skippedDuplicates.ToString() & vbCrLf & _
            If(openingsReused = 0, "", "Existing plate holes kept: " & openingsReused.ToString() & vbCrLf) & _
            If(excluded.Count = 0, "", vbCrLf & "Selections skipped:" & vbCrLf & _
                String.Join(vbCrLf, excluded.ToArray()) & vbCrLf) & _
            If(namingWarnings.Count = 0, "", vbCrLf & "Naming notes (geometry was created):" & vbCrLf & _
                String.Join(vbCrLf, namingWarnings.ToArray()) & vbCrLf) & vbCrLf & _
            washerSummary & vbCrLf & vbCrLf & _
            "Inspect the plate, dimensions, and hardware clearances, then SAVE the plate .ipt and assembly.", _
            "Grouped Mounting Hardware")
    Catch ex As System.Exception
        If progress IsNot Nothing Then
            Try
                progress.Close()
            Catch
            End Try
            progress = Nothing
        End If
        If trans IsNot Nothing Then
            Try
                trans.Abort()
            Catch
            End Try
        End If
        System.Windows.Forms.MessageBox.Show( _
            "Hole creation failed; attempted to roll back the group transaction." & vbCrLf & _
            "Operation: " & operationInfo & vbCrLf & vbCrLf & _
            ex.ToString(), "Grouped Mounting Hardware - error")
    End Try
End Sub


' ================================================================
' INVENTOR 2027 INTERACTIVE SELECTION
' InteractionEvents, unlike CommandManager.Pick, provides an explicit
' Finish Selection / Cancel workflow without depending on ESC.
' Autodesk API: InteractionEvents.SelectEvents.OnSelect.
' ================================================================
Public Class MGHInteractionSelector
    Private WithEvents oInteraction As Inventor.InteractionEvents
    Private WithEvents oSelect As Inventor.SelectEvents
    Private palette As MGHSelectionPalette
    Private completed As Boolean
    Private approved As Boolean
    Private automaticFinish As Boolean
    Private highlightSet As Inventor.HighlightSet
    Private highlightRims As Boolean
    Public Picked As New System.Collections.Generic.List(Of Object)()

    Public Function Run(app As Inventor.Application, _
                        filter As Inventor.SelectionFilterEnum, _
                        caption As String, instructions As String, _
                        finishAfterFirst As Boolean) As Boolean
        Picked.Clear()
        completed = False
        approved = False
        automaticFinish = finishAfterFirst
        highlightRims = Not finishAfterFirst
        highlightSet = Nothing
        Try
            palette = New MGHSelectionPalette(caption, instructions, finishAfterFirst)
            AddHandler palette.FinishPressed, AddressOf UserFinished
            AddHandler palette.CancelPressed, AddressOf UserCanceled
            AddHandler palette.FormClosed, AddressOf PaletteClosed

            oInteraction = app.CommandManager.CreateInteractionEvents()
            oInteraction.InteractionDisabled = False
            oInteraction.StatusBarText = instructions
            oSelect = oInteraction.SelectEvents
            oSelect.AddSelectionFilter(filter)
            oSelect.SingleSelectEnabled = finishAfterFirst
            ' Hole picking accepts a drag box as well as a click. The plate face
            ' and the hardware mounting face stay one click.
            If Not finishAfterFirst Then
                Try
                    oSelect.WindowSelectEnabled = True
                    oSelect.AddWindowSelectionFilter(filter)
                Catch
                End Try
            End If

            ' Keep ALL selected hole rims visibly highlighted during the session.
            ' HighlightSet is supported in assembly documents and works with proxies.
            If highlightRims Then
                Try
                    Dim assyDoc As Inventor.AssemblyDocument = TryCast(app.ActiveDocument, Inventor.AssemblyDocument)
                    If assyDoc IsNot Nothing Then
                        highlightSet = assyDoc.CreateHighlightSet()
                        highlightSet.Color = app.TransientObjects.CreateColor(0, 220, 255)
                    End If
                Catch
                    ' If Inventor cannot highlight a particular document/context,
                    ' selection and hole creation must still work.
                    highlightSet = Nothing
                End Try
            End If

            palette.Show()  ' Modeless: user continues clicking Inventor geometry.
            oInteraction.Start()
            Do While Not completed
                app.UserInterfaceManager.DoEvents()
                ' Maintain message pumping in Inventor's own STA thread.
                System.Threading.Thread.Sleep(12)
            Loop
            Return approved
        Catch ex As System.Exception
            System.Windows.Forms.MessageBox.Show( _
                "Selection could not be completed:" & vbCrLf & ex.Message, _
                "Grouped Mounting Hardware - selection error")
            Return False
        Finally
            completed = True
            If oInteraction IsNot Nothing Then
                Try
                    oInteraction.Stop()
                Catch
                End Try
            End If
            oSelect = Nothing
            oInteraction = Nothing
            If highlightSet IsNot Nothing Then
                Try
                    highlightSet.Clear()
                    highlightSet.Delete()
                Catch
                End Try
                highlightSet = Nothing
            End If
            If palette IsNot Nothing Then
                Try
                    palette.Close()
                    palette.Dispose()
                Catch
                End Try
                palette = Nothing
            End If
        End Try
    End Function

    Private Sub SelectedGeometry(JustSelectedEntities As Inventor.ObjectsEnumerator, _
        SelectionDevice As Inventor.SelectionDeviceEnum, _
        ModelPosition As Inventor.Point, ViewPosition As Inventor.Point2d, _
        View As Inventor.View) Handles oSelect.OnSelect
        If completed Then Exit Sub
        ' Use JustSelectedEntities directly: the event can fire before the
        ' SelectedEntities collection is fully refreshed in some versions.
        For Each ent As Object In JustSelectedEntities
            If ent Is Nothing Then Continue For
            If MGHSelectionAlreadyPicked(Picked, ent) Then Continue For
            ' A box can cross arc edges of a countersink. Keep full circles only.
            If highlightRims AndAlso Not MGHSelectionIsFullCircle(ent) Then Continue For
            Picked.Add(ent)
        Next
        RefreshRimHighlight()
        If palette IsNot Nothing Then palette.SetSelectedCount(Picked.Count)
        If automaticFinish AndAlso Picked.Count > 0 Then
            approved = True
            completed = True
        End If
    End Sub

    Private Sub UnselectedGeometry(UnSelectedEntities As Inventor.ObjectsEnumerator, _
        SelectionDevice As Inventor.SelectionDeviceEnum, _
        ModelPosition As Inventor.Point, ViewPosition As Inventor.Point2d, _
        View As Inventor.View) Handles oSelect.OnUnSelect
        If Not completed Then RefreshSelectedEntities()
    End Sub

    Private Sub RefreshSelectedEntities()
        If oSelect Is Nothing Then Exit Sub
        Picked.Clear()
        Try
            For Each ent As Object In oSelect.SelectedEntities
                If ent IsNot Nothing Then Picked.Add(ent)
            Next
        Catch
            ' OnSelect's JustSelectedEntities fallback remains available.
        End Try
        RefreshRimHighlight()
        If palette IsNot Nothing Then palette.SetSelectedCount(Picked.Count)
    End Sub

    Private Sub RefreshRimHighlight()
        If highlightSet Is Nothing Then Exit Sub
        Try
            highlightSet.Clear()
            For Each ent As Object In Picked
                Try
                    Dim face As Inventor.FaceProxy = TryCast(ent, Inventor.FaceProxy)
                    If face Is Nothing Then
                        ' If user selects an edge, highlight that exact rim.
                        highlightSet.AddItem(ent)
                    Else
                        ' A face selection highlights its circular rims.
                        Dim foundRims As Boolean = False
                        For Each e As Object In face.Edges
                            Try
                                Dim rim As Inventor.EdgeProxy = TryCast(e, Inventor.EdgeProxy)
                                If rim IsNot Nothing AndAlso TypeOf rim.Geometry Is Inventor.Circle Then
                                    highlightSet.AddItem(rim)
                                    foundRims = True
                                End If
                            Catch
                            End Try
                        Next
                        If Not foundRims Then highlightSet.AddItem(face)
                    End If
                Catch
                    ' A single unhighlightable rim must not cancel the tool.
                End Try
            Next
        Catch
        End Try
    End Sub

    Private Sub InteractionTerminated() Handles oInteraction.OnTerminate
        ' Esc or a competing Inventor command should never hang the rule.
        ' Explicit Finish button is the normal way to proceed.
        If Not completed Then
            approved = False
            completed = True
        End If
    End Sub

    Private Function MGHSelectionAlreadyPicked(items As System.Collections.Generic.List(Of Object), candidate As Object) As Boolean
        If items Is Nothing OrElse candidate Is Nothing Then Return False
        For Each known As Object In items
            If known Is candidate Then Return True
        Next
        Return False
    End Function

    Private Function MGHSelectionIsFullCircle(ent As Object) As Boolean
        Dim edge As Inventor.Edge = Nothing
        Dim proxy As Inventor.EdgeProxy = TryCast(ent, Inventor.EdgeProxy)
        If proxy IsNot Nothing Then
            edge = proxy
        Else
            edge = TryCast(ent, Inventor.Edge)
        End If
        If edge Is Nothing Then Return False
        Try
            Dim circ As Inventor.Circle = TryCast(edge.Geometry, Inventor.Circle)
            Return circ IsNot Nothing AndAlso circ.Radius > 0
        Catch
            Return False
        End Try
    End Function

    Private Sub UserFinished(sender As Object, e As System.EventArgs)
        If Picked.Count = 0 Then
            System.Windows.Forms.MessageBox.Show( _
                "Select at least one mounting hole before finishing, or click Cancel.", _
                "No holes selected")
            Exit Sub
        End If
        approved = True
        completed = True
    End Sub

    Private Sub UserCanceled(sender As Object, e As System.EventArgs)
        approved = False
        completed = True
    End Sub

    Private Sub PaletteClosed(sender As Object, e As System.Windows.Forms.FormClosedEventArgs)
        If Not completed Then
            approved = False
            completed = True
        End If
    End Sub
End Class

Public Class MGHSelectionPalette
    Inherits System.Windows.Forms.Form

    Public Event FinishPressed As System.EventHandler
    Public Event CancelPressed As System.EventHandler
    Private countLabel As System.Windows.Forms.Label
    Private multiPick As Boolean

    Public Sub New(caption As String, instructions As String, singlePick As Boolean)
        MyBase.New()
        Me.Text = caption
        Me.Width = 490
        Me.Height = 230
        Me.StartPosition = System.Windows.Forms.FormStartPosition.CenterScreen
        Me.FormBorderStyle = System.Windows.Forms.FormBorderStyle.FixedToolWindow
        Me.TopMost = True
        Me.ShowInTaskbar = False
        Me.MaximizeBox = False
        Me.MinimizeBox = False
        multiPick = Not singlePick

        Dim directions As New System.Windows.Forms.Label()
        directions.Text = instructions
        directions.Left = 14 : directions.Top = 14
        directions.Width = 450 : directions.Height = 78
        Me.Controls.Add(directions)

        countLabel = New System.Windows.Forms.Label()
        countLabel.Left = 14 : countLabel.Top = 96
        countLabel.Width = 450 : countLabel.Height = 24
        If singlePick Then
            countLabel.Text = "Click the face. Cancel skips it."
        Else
            countLabel.Text = "Selected: 0 (click a rim or drag a box)"
        End If
        Me.Controls.Add(countLabel)

        Dim cancelBtn As New System.Windows.Forms.Button()
        cancelBtn.Text = "Cancel Without Changes"
        cancelBtn.Width = 165 : cancelBtn.Left = 14 : cancelBtn.Top = 128
        AddHandler cancelBtn.Click, AddressOf CancelClick
        Me.Controls.Add(cancelBtn)

        If Not singlePick Then
            Dim finishBtn As New System.Windows.Forms.Button()
            finishBtn.Text = "Finish Selection && Review"
            finishBtn.Width = 190 : finishBtn.Left = 270 : finishBtn.Top = 128
            AddHandler finishBtn.Click, AddressOf FinishClick
            Me.Controls.Add(finishBtn)
        End If
        ' Do NOT set Form.AcceptButton or Form.CancelButton: in Inventor
        ' 2027 iLogic those assignments can invoke System.Private.Windows.Core.
    End Sub

    Public Sub SetSelectedCount(n As Integer)
        If multiPick Then
            countLabel.Text = "Selected: " & n.ToString() & " (click a rim or drag a box)"
        Else
            countLabel.Text = "Selected: " & n.ToString()
        End If
    End Sub

    Private Sub FinishClick(sender As Object, e As System.EventArgs)
        RaiseEvent FinishPressed(Me, System.EventArgs.Empty)
    End Sub

    Private Sub CancelClick(sender As Object, e As System.EventArgs)
        RaiseEvent CancelPressed(Me, System.EventArgs.Empty)
    End Sub
End Class

' Nut side is the hole rim or the plate face. The screw uses the other side.
Public Class MGHWasherSideDialog
    Inherits System.Windows.Forms.Form
    Private libraryBox As System.Windows.Forms.TextBox
    Private nutOnRim As System.Windows.Forms.RadioButton
    Private screwBox As System.Windows.Forms.CheckBox
    Private washerUnderScrewBox As System.Windows.Forms.CheckBox
    Private washerUnderNutBox As System.Windows.Forms.CheckBox
    Private nutBox As System.Windows.Forms.CheckBox
    Public NutOnSelectedRim As Boolean
    Public WasherUnderScrew As Boolean
    Public WasherUnderNut As Boolean
    Public PlaceNut As Boolean
    Public PlaceScrew As Boolean
    Public LibraryPath As String

    Public Sub New(initialLibrary As String)
        MyBase.New()
        Me.Text = "Place hardware?"
        Me.Width = 560 : Me.Height = 530
        Me.FormBorderStyle = System.Windows.Forms.FormBorderStyle.FixedDialog
        Me.StartPosition = System.Windows.Forms.FormStartPosition.CenterScreen
        Me.MaximizeBox = False : Me.MinimizeBox = False
        Dim note As New System.Windows.Forms.Label()
        note.Left = 14 : note.Top = 12 : note.Width = 516 : note.Height = 74
        note.Text = "The nut goes on the hole rim you clicked, or on the plate face you selected first." & vbCrLf & _
            "A washer under the nut sits on that side. A washer under the screw sits on the other side." & vbCrLf & _
            "The screw length covers the distance between those faces plus the washers and the nut."
        Me.Controls.Add(note)
        Dim libraryLabel As New System.Windows.Forms.Label()
        libraryLabel.Left = 14 : libraryLabel.Top = 96 : libraryLabel.Width = 80 : libraryLabel.Height = 22
        libraryLabel.Text = "Library"
        Me.Controls.Add(libraryLabel)
        libraryBox = New System.Windows.Forms.TextBox()
        libraryBox.Left = 100 : libraryBox.Top = 94 : libraryBox.Width = 424 : libraryBox.Height = 22
        libraryBox.ReadOnly = True
        libraryBox.Text = initialLibrary
        Me.Controls.Add(libraryBox)
        Dim changeBtn As New System.Windows.Forms.Button()
        changeBtn.Text = "Change Hardware Folder"
        changeBtn.Left = 14 : changeBtn.Top = 124 : changeBtn.Width = 200 : changeBtn.Height = 28
        AddHandler changeBtn.Click, AddressOf ChangeLibrary
        Me.Controls.Add(changeBtn)

        Dim nutGroup As New System.Windows.Forms.GroupBox()
        nutGroup.Text = "Nut is on"
        nutGroup.Left = 14 : nutGroup.Top = 164 : nutGroup.Width = 516 : nutGroup.Height = 72
        nutOnRim = New System.Windows.Forms.RadioButton()
        nutOnRim.Text = "Hole rim I clicked"
        nutOnRim.Left = 16 : nutOnRim.Top = 28 : nutOnRim.Width = 220 : nutOnRim.Height = 24
        nutGroup.Controls.Add(nutOnRim)
        Dim nutOpposite As New System.Windows.Forms.RadioButton()
        nutOpposite.Text = "Plate face I selected"
        nutOpposite.Left = 250 : nutOpposite.Top = 28 : nutOpposite.Width = 240 : nutOpposite.Height = 24
        nutOpposite.Checked = True
        nutGroup.Controls.Add(nutOpposite)
        Me.Controls.Add(nutGroup)

        Dim placeGroup As New System.Windows.Forms.GroupBox()
        placeGroup.Text = "Place"
        placeGroup.Left = 14 : placeGroup.Top = 246 : placeGroup.Width = 516 : placeGroup.Height = 148
        screwBox = New System.Windows.Forms.CheckBox()
        screwBox.Text = "Screw"
        screwBox.Left = 16 : screwBox.Top = 28 : screwBox.Width = 470 : screwBox.Height = 24
        placeGroup.Controls.Add(screwBox)
        washerUnderScrewBox = New System.Windows.Forms.CheckBox()
        washerUnderScrewBox.Text = "Washer under screw"
        washerUnderScrewBox.Left = 16 : washerUnderScrewBox.Top = 54 : washerUnderScrewBox.Width = 470 : washerUnderScrewBox.Height = 24
        placeGroup.Controls.Add(washerUnderScrewBox)
        washerUnderNutBox = New System.Windows.Forms.CheckBox()
        washerUnderNutBox.Text = "Washer under nut"
        washerUnderNutBox.Checked = True
        washerUnderNutBox.Left = 16 : washerUnderNutBox.Top = 80 : washerUnderNutBox.Width = 470 : washerUnderNutBox.Height = 24
        placeGroup.Controls.Add(washerUnderNutBox)
        nutBox = New System.Windows.Forms.CheckBox()
        nutBox.Text = "Nut"
        nutBox.Left = 16 : nutBox.Top = 106 : nutBox.Width = 470 : nutBox.Height = 24
        placeGroup.Controls.Add(nutBox)
        Me.Controls.Add(placeGroup)

        Dim placeBtn As New System.Windows.Forms.Button()
        placeBtn.Text = "Place Hardware"
        placeBtn.Left = 14 : placeBtn.Top = 410 : placeBtn.Width = 160 : placeBtn.Height = 32
        AddHandler placeBtn.Click, AddressOf PlaceHardware
        Me.Controls.Add(placeBtn)
        Dim skipBtn As New System.Windows.Forms.Button()
        skipBtn.Text = "Skip Hardware"
        skipBtn.Left = 370 : skipBtn.Top = 410 : skipBtn.Width = 160 : skipBtn.Height = 32
        AddHandler skipBtn.Click, AddressOf SkipWashers
        Me.Controls.Add(skipBtn)
    End Sub

    Private Sub PlaceHardware(sender As Object, e As System.EventArgs)
        If Not screwBox.Checked AndAlso Not washerUnderScrewBox.Checked AndAlso Not washerUnderNutBox.Checked AndAlso Not nutBox.Checked Then
            System.Windows.Forms.MessageBox.Show("Check a screw, washer, or nut to place, or click Skip Hardware.", "Place hardware?")
            Exit Sub
        End If
        LibraryPath = libraryBox.Text.Trim()
        NutOnSelectedRim = nutOnRim.Checked
        WasherUnderScrew = washerUnderScrewBox.Checked
        WasherUnderNut = washerUnderNutBox.Checked
        PlaceNut = nutBox.Checked
        PlaceScrew = screwBox.Checked
        Me.DialogResult = System.Windows.Forms.DialogResult.OK
        Me.Close()
    End Sub
    Private Sub ChangeLibrary(sender As Object, e As System.EventArgs)
        Dim browser As New System.Windows.Forms.FolderBrowserDialog()
        browser.Description = "Select the hardware folder. Each size folder, such as #8, should contain Washers, Nuts, and Screws folders."
        browser.ShowNewFolderButton = False
        If System.IO.Directory.Exists(libraryBox.Text) Then browser.SelectedPath = libraryBox.Text
        If browser.ShowDialog() = System.Windows.Forms.DialogResult.OK AndAlso browser.SelectedPath <> "" Then
            libraryBox.Text = browser.SelectedPath
        End If
        browser.Dispose()
    End Sub
    Private Sub SkipWashers(sender As Object, e As System.EventArgs)
        Me.DialogResult = System.Windows.Forms.DialogResult.Cancel
        Me.Close()
    End Sub
End Class

' The component hole the user clicked. CenterX/Y/Z are assembly coordinates of that rim.
' One chosen screw for every hole of a size that needs this length.
Public Class MGHScrewRequest
    Public Key As String
    Public SizeName As String
    Public RequiredInches As Double
    Public GripIn As Double
    Public ScrewWasherIn As Double
    Public NutWasherIn As Double
    Public NutIn As Double
    Public HoleCount As Integer
    Public GroupLabels As New System.Collections.Generic.List(Of String)()

    Public Function LabelText() As String
        If GroupLabels Is Nothing OrElse GroupLabels.Count = 0 Then Return ""
        Return String.Join(", ", GroupLabels.ToArray())
    End Function
End Class

Public Class MGHComponentRim
    Public Component As Inventor.ComponentOccurrence
    Public SelectedEdge As Inventor.Edge
    Public CenterX As Double
    Public CenterY As Double
    Public CenterZ As Double
    Public AxisX As Double
    Public AxisY As Double
    Public AxisZ As Double
    Public Radius As Double
End Class

Public Class MGHRimCandidate
    Public X As Double
    Public Y As Double
    Public Z As Double
    Public Radius As Double
End Class

Public Class MountPoint
    Public Center As Inventor.Point
    Public SourceDiameterIn As Double
    Public SourceName As String
    Public Rim As MGHComponentRim
    Public ExistingOpening As Boolean
End Class

Public Class InputBucket
    Public SourceKey As String
    Public Centers As New System.Collections.Generic.List(Of Inventor.Point)()
    Public Rims As New System.Collections.Generic.List(Of MGHComponentRim)()
    Public ExistingOpening As New System.Collections.Generic.List(Of Boolean)()
    Public Screw As String
    Public Fit As String
    Public DiameterIn As Double
    Public GroupLabel As String
    Public Mode As String = "Clearance"
    Public Seat As String = "None"
    Public SeatDiameterIn As Double = 0
    Public SeatDepthIn As Double = 0
    Public SeatAngleDeg As Double = 0
    Public ThreadType As String = "ANSI Unified Screw Threads"
    Public ThreadDesignation As String = ""
    Public ThreadClass As String = "2B"
    Public ClearanceStandard As String = "Ansi Unified Screw Threads"
    Public ClearanceFamily As String = "Flat Head Machine Screw (100)"
End Class

Public Class OutputGroup
    Public Key As String
    Public Label As String
    Public DiameterIn As Double
    Public Screw As String
    Public Fit As String
    Public Mode As String
    Public Seat As String
    Public SeatDiameterIn As Double
    Public SeatDepthIn As Double
    Public SeatAngleDeg As Double
    Public ThreadType As String
    Public ThreadDesignation As String
    Public ThreadClass As String
    Public ClearanceStandard As String
    Public ClearanceFamily As String
    Public LegacyKey As String
    Public PlaneId As String
    Public Centers As New System.Collections.Generic.List(Of Inventor.Point)()
    Public Rims As New System.Collections.Generic.List(Of MGHComponentRim)()
    ' Centers that still have plate material. OpeningCenters already have a hole.
    Public CentersToCut As New System.Collections.Generic.List(Of Inventor.Point)()
    Public OpeningCenters As New System.Collections.Generic.List(Of Inventor.Point)()
End Class

' Parsed form of a feature's stored identity. SpecKey excludes the group name.
Public Class MGHParsedKey
    Public SpecKey As String
    Public Label As String
    Public Kind As String
    Public SizeKey As String
End Class

Public Class MGHIndexedFeature
    Public Feature As Inventor.HoleFeature
    Public SpecKey As String
    Public SizeKey As String
    Public Label As String
    Public Kind As String
End Class

Public Class MGHFeatureIndex
    Public BySpec As New System.Collections.Generic.Dictionary(Of String, Inventor.HoleFeature)(System.StringComparer.Ordinal)
    Public ByV15Size As New System.Collections.Generic.Dictionary(Of String, Inventor.HoleFeature)(System.StringComparer.Ordinal)
    Public LabelBySpec As New System.Collections.Generic.Dictionary(Of String, String)(System.StringComparer.Ordinal)
    Public LabelByV15 As New System.Collections.Generic.Dictionary(Of String, String)(System.StringComparer.Ordinal)
    Public Items As New System.Collections.Generic.List(Of MGHIndexedFeature)()
End Class

Function MGHSizeKey(planeId As String, screw As String, fit As String, diameterText As String) As String
    Return planeId & "|" & screw & "|" & fit & "|" & diameterText
End Function

Function MGHBuildSpecKey(planeId As String, screw As String, fit As String, diameterText As String, _
    mode As String, seat As String, seatDiameterText As String, seatDepthText As String, seatAngleText As String, _
    threadType As String, threadDesignation As String, threadClass As String, _
    clearanceStandard As String, clearanceFamily As String) As String
    Return MGHSizeKey(planeId, screw, fit, diameterText) & "|V17|" & _
        mode.Trim().ToUpperInvariant() & "|" & seat.Trim().ToUpperInvariant() & "|" & _
        seatDiameterText & "|" & seatDepthText & "|" & seatAngleText & "|" & _
        threadType.Trim().ToUpperInvariant() & "|" & threadDesignation.Trim().ToUpperInvariant() & "|" & _
        threadClass.Trim().ToUpperInvariant() & "|" & _
        clearanceStandard.Trim().ToUpperInvariant() & "|" & clearanceFamily.Trim().ToUpperInvariant()
End Function

Function MGHSpecKeyFromBucket(planeId As String, b As InputBucket) As String
    Return MGHBuildSpecKey(planeId, b.Screw, b.Fit, _
        b.DiameterIn.ToString("0.000000", System.Globalization.CultureInfo.InvariantCulture), _
        b.Mode, b.Seat, _
        b.SeatDiameterIn.ToString("0.000000", System.Globalization.CultureInfo.InvariantCulture), _
        b.SeatDepthIn.ToString("0.000000", System.Globalization.CultureInfo.InvariantCulture), _
        b.SeatAngleDeg.ToString("0.0000", System.Globalization.CultureInfo.InvariantCulture), _
        b.ThreadType, b.ThreadDesignation, b.ThreadClass, b.ClearanceStandard, b.ClearanceFamily)
End Function

Function MGHJoinFields(parts As String(), startIndex As Integer, endIndex As Integer) As String
    Dim joined As New System.Text.StringBuilder()
    Dim i As Integer
    For i = startIndex To endIndex
        If i > startIndex Then joined.Append("|"c)
        joined.Append(parts(i))
    Next
    Return joined.ToString()
End Function

Function MGHIsStoredMode(token As String) As Boolean
    Return token = "CLEARANCE" OrElse token = "THREADED" OrElse token = "CUSTOM/PRESS-FIT"
End Function

' V1.5 keys are plane|screw|fit|diameter|label.
' V1.6 keys insert the label before a V16 token. V1.7 keys have no label; V17 is the fifth field.
Function MGHParseStoredGroupKey(saved As String) As MGHParsedKey
    Dim parsed As New MGHParsedKey()
    parsed.Kind = "Unknown"
    parsed.SpecKey = ""
    parsed.Label = ""
    parsed.SizeKey = ""
    If saved Is Nothing Then Return parsed
    Dim parts As String() = saved.Split("|"c)
    If parts.Length < 4 Then Return parsed
    parsed.SizeKey = MGHJoinFields(parts, 0, 3)
    Dim marker As Integer = -1
    Dim i As Integer
    For i = 0 To parts.Length - 2
        If (parts(i) = "V16" OrElse parts(i) = "V17") AndAlso MGHIsStoredMode(parts(i + 1)) Then marker = i
    Next
    If marker < 0 Then
        parsed.Kind = "V15"
        If parts.Length > 4 Then parsed.Label = MGHJoinFields(parts, 4, parts.Length - 1)
        Return parsed
    End If
    parsed.Kind = If(parts(marker) = "V17" AndAlso marker = 4, "V17", "V16")
    If marker > 4 Then parsed.Label = MGHJoinFields(parts, 4, marker - 1)
    parsed.SpecKey = parsed.SizeKey & "|V17|" & MGHJoinFields(parts, marker + 1, parts.Length - 1)
    Return parsed
End Function

Sub MGHRequireStorable(fieldName As String, value As String)
    If value IsNot Nothing AndAlso value.Length > 255 Then
        Throw New System.Exception(fieldName & " is " & value.Length.ToString() & _
            " characters. Inventor stores each identity field in its own string attribute, which holds 255 characters. Shorten it before generating holes.")
    End If
End Sub

Function MGHSpecConflictMessage(existingName As String, existingLabel As String, requestedLabel As String) As String
    Dim shownExisting As String = existingLabel
    If shownExisting Is Nothing OrElse shownExisting = "" Then shownExisting = "(unnamed)"
    Dim shownRequested As String = requestedLabel
    If shownRequested Is Nothing OrElse shownRequested = "" Then shownRequested = "(unnamed)"
    Return "An existing grouped hole already uses one of these locations, and this specification will not edit that feature." & vbCrLf & _
        "The group name is stored separately. A name-only change updates the existing feature." & vbCrLf & _
        "Fit, diameter, seat, thread, and clearance changes are a different specification, so they are left on the existing feature." & vbCrLf & _
        "Existing feature: " & existingName & vbCrLf & _
        "Existing group name: " & shownExisting & vbCrLf & _
        "Requested group name: " & shownRequested & vbCrLf & _
        "No holes were created."
End Function

Function MGHGetAttr(aset As Inventor.AttributeSet, name As String) As String
    If aset Is Nothing OrElse Not aset.NameIsUsed(name) Then Return ""
    Dim raw As Object = aset.Item(name).Value
    If raw Is Nothing Then Return ""
    Return CStr(raw)
End Function

Sub MGHPutAttr(aset As Inventor.AttributeSet, name As String, value As String)
    If value Is Nothing Then value = ""
    MGHRequireStorable(name, value)
    If aset.NameIsUsed(name) Then
        aset.Item(name).Value = value
    Else
        aset.Add(name, Inventor.ValueTypeEnum.kStringType, value)
    End If
End Sub

Function MGHReadIdentity(aset As Inventor.AttributeSet) As MGHParsedKey
    If String.Equals(MGHGetAttr(aset, "Schema"), "V17", System.StringComparison.Ordinal) Then
        Dim current As New MGHParsedKey()
        current.Kind = "V17"
        current.Label = MGHGetAttr(aset, "GroupLabel")
        current.SizeKey = MGHSizeKey(MGHGetAttr(aset, "PlaneId"), MGHGetAttr(aset, "Screw"), _
            MGHGetAttr(aset, "Fit"), MGHGetAttr(aset, "Diameter"))
        current.SpecKey = MGHBuildSpecKey(MGHGetAttr(aset, "PlaneId"), MGHGetAttr(aset, "Screw"), _
            MGHGetAttr(aset, "Fit"), MGHGetAttr(aset, "Diameter"), _
            MGHGetAttr(aset, "Mode"), MGHGetAttr(aset, "Seat"), _
            MGHGetAttr(aset, "SeatDiameter"), MGHGetAttr(aset, "SeatDepth"), MGHGetAttr(aset, "SeatAngle"), _
            MGHGetAttr(aset, "ThreadType"), MGHGetAttr(aset, "ThreadDesignation"), MGHGetAttr(aset, "ThreadClass"), _
            MGHGetAttr(aset, "ClearanceStandard"), MGHGetAttr(aset, "ClearanceFamily"))
        Return current
    End If
    If aset.NameIsUsed("GroupKey") Then Return MGHParseStoredGroupKey(CStr(aset.Item("GroupKey").Value))
    Return Nothing
End Function

Function MGHLoadFeatureIndex(def As Inventor.PartComponentDefinition) As MGHFeatureIndex
    Dim index As New MGHFeatureIndex()
    Dim holes As Inventor.HoleFeatures = def.Features.HoleFeatures
    For Each feat As Inventor.HoleFeature In holes
        Try
            If Not feat.AttributeSets.NameIsUsed("MGH_Generator") Then Continue For
            Dim parsed As MGHParsedKey = MGHReadIdentity(feat.AttributeSets.Item("MGH_Generator"))
            If parsed Is Nothing OrElse parsed.Kind = "Unknown" Then Continue For
            Dim item As New MGHIndexedFeature()
            item.Feature = feat
            item.Label = parsed.Label
            item.Kind = parsed.Kind
            item.SpecKey = parsed.SpecKey
            item.SizeKey = parsed.SizeKey
            index.Items.Add(item)
            If parsed.Kind = "V15" Then
                If parsed.SizeKey = "" Then Continue For
                If index.ByV15Size.ContainsKey(parsed.SizeKey) Then
                    Throw New System.Exception("Two existing holes share the same V1.5 clearance identity (" & _
                        index.ByV15Size(parsed.SizeKey).Name & " and " & feat.Name & ").")
                End If
                index.ByV15Size.Add(parsed.SizeKey, feat)
                index.LabelByV15.Add(parsed.SizeKey, parsed.Label)
            Else
                If parsed.SpecKey = "" Then Continue For
                If index.BySpec.ContainsKey(parsed.SpecKey) Then
                    Throw New System.Exception("Two existing grouped holes have the same specification (" & _
                        index.BySpec(parsed.SpecKey).Name & " and " & feat.Name & "). The group name is not part of the identity, so only one can remain.")
                End If
                index.BySpec.Add(parsed.SpecKey, feat)
                index.LabelBySpec.Add(parsed.SpecKey, parsed.Label)
            End If
        Catch ex As System.Exception
            If ex.Message.StartsWith("Two existing") Then Throw
        End Try
    Next
    Return index
End Function

Sub MGHApplyStoredLabels(buckets As System.Collections.Generic.SortedDictionary(Of String, InputBucket), _
    def As Inventor.PartComponentDefinition, planeId As String)
    Dim index As MGHFeatureIndex = MGHLoadFeatureIndex(def)
    For Each b As InputBucket In buckets.Values
        Dim spec As String = MGHSpecKeyFromBucket(planeId, b)
        Dim sizeKey As String = MGHSizeKey(planeId, b.Screw, b.Fit, _
            b.DiameterIn.ToString("0.000000", System.Globalization.CultureInfo.InvariantCulture))
        Dim stored As String = ""
        If index.LabelBySpec.ContainsKey(spec) Then
            stored = index.LabelBySpec(spec)
        ElseIf b.Mode = "Clearance" AndAlso b.Seat = "None" AndAlso index.LabelByV15.ContainsKey(sizeKey) Then
            stored = index.LabelByV15(sizeKey)
        End If
        If stored <> "" Then b.GroupLabel = stored
    Next
End Sub

Function MGHFeatureModelCenters(feat As Inventor.HoleFeature) As System.Collections.Generic.List(Of Inventor.Point)
    Dim result As New System.Collections.Generic.List(Of Inventor.Point)()
    Try
        Dim placement As Inventor.SketchHolePlacementDefinition = TryCast(feat.PlacementDefinition, Inventor.SketchHolePlacementDefinition)
        If placement Is Nothing OrElse feat.Sketch Is Nothing Then Return result
        For Each sp As Inventor.SketchPoint In placement.HoleCenterPoints
            result.Add(feat.Sketch.SketchToModelSpace(sp.Geometry))
        Next
    Catch
    End Try
    Return result
End Function

Function MGHSharesAnyCenter(feat As Inventor.HoleFeature, centers As System.Collections.Generic.List(Of Inventor.Point)) As Boolean
    For Each existingCenter As Inventor.Point In MGHFeatureModelCenters(feat)
        For Each requested As Inventor.Point In centers
            If existingCenter.DistanceTo(requested) < 0.005 Then Return True
        Next
    Next
    Return False
End Function

Function MGHDescribeExistingGroups(def As Inventor.PartComponentDefinition, _
    groups As System.Collections.Generic.SortedDictionary(Of String, OutputGroup)) As System.Collections.Generic.List(Of String)
    Dim notes As New System.Collections.Generic.List(Of String)()
    Dim index As MGHFeatureIndex = MGHLoadFeatureIndex(def)
    For Each g As OutputGroup In groups.Values
        Dim matchFeat As Inventor.HoleFeature = Nothing
        Dim storedLabel As String = ""
        If index.BySpec.ContainsKey(g.Key) Then
            matchFeat = index.BySpec(g.Key)
            storedLabel = index.LabelBySpec(g.Key)
        ElseIf g.Mode = "Clearance" AndAlso g.Seat = "None" AndAlso index.ByV15Size.ContainsKey(g.LegacyKey) Then
            matchFeat = index.ByV15Size(g.LegacyKey)
            storedLabel = index.LabelByV15(g.LegacyKey)
        End If
        If matchFeat IsNot Nothing Then
            If storedLabel <> "" AndAlso Not String.Equals(storedLabel, g.Label, System.StringComparison.Ordinal) Then
                notes.Add("""" & storedLabel & """ will be renamed to """ & g.Label & """ on " & matchFeat.Name & ".")
            End If
        Else
            For Each item As MGHIndexedFeature In index.Items
                If MGHSharesAnyCenter(item.Feature, g.CentersToCut) Then
                    Throw New System.Exception(MGHSpecConflictMessage(item.Feature.Name, item.Label, g.Label))
                End If
            Next
        End If
    Next
    Return notes
End Function

Function MGHIdentitySet(h As Inventor.HoleFeature) As Inventor.AttributeSet
    If h.AttributeSets.NameIsUsed("MGH_Generator") Then
        Dim existingSet As Inventor.AttributeSet = h.AttributeSets.Item("MGH_Generator")
        Dim copies As Boolean = False
        Try
            copies = existingSet.CopyWithOwner
        Catch
        End Try
        If copies AndAlso String.Equals(MGHGetAttr(existingSet, "Schema"), "V17", System.StringComparison.Ordinal) Then
            Return existingSet
        End If
        existingSet.Delete()
    End If
    Return h.AttributeSets.Add("MGH_Generator", True)
End Function

Sub MGHWriteIdentityFields(aset As Inventor.AttributeSet, g As OutputGroup)
    MGHPutAttr(aset, "Schema", "V17")
    MGHPutAttr(aset, "PlaneId", g.PlaneId)
    MGHPutAttr(aset, "Screw", g.Screw)
    MGHPutAttr(aset, "Fit", g.Fit)
    MGHPutAttr(aset, "Diameter", g.DiameterIn.ToString("0.000000", System.Globalization.CultureInfo.InvariantCulture))
    MGHPutAttr(aset, "Mode", g.Mode.Trim().ToUpperInvariant())
    MGHPutAttr(aset, "Seat", g.Seat.Trim().ToUpperInvariant())
    MGHPutAttr(aset, "SeatDiameter", g.SeatDiameterIn.ToString("0.000000", System.Globalization.CultureInfo.InvariantCulture))
    MGHPutAttr(aset, "SeatDepth", g.SeatDepthIn.ToString("0.000000", System.Globalization.CultureInfo.InvariantCulture))
    MGHPutAttr(aset, "SeatAngle", g.SeatAngleDeg.ToString("0.0000", System.Globalization.CultureInfo.InvariantCulture))
    MGHPutAttr(aset, "ThreadType", g.ThreadType.Trim().ToUpperInvariant())
    MGHPutAttr(aset, "ThreadDesignation", g.ThreadDesignation.Trim().ToUpperInvariant())
    MGHPutAttr(aset, "ThreadClass", g.ThreadClass.Trim().ToUpperInvariant())
    MGHPutAttr(aset, "ClearanceStandard", g.ClearanceStandard.Trim().ToUpperInvariant())
    MGHPutAttr(aset, "ClearanceFamily", g.ClearanceFamily.Trim().ToUpperInvariant())
    MGHPutAttr(aset, "GroupLabel", g.Label)
    If aset.NameIsUsed("GroupKey") Then aset.Item("GroupKey").Delete()
End Sub

' Returns True when an existing feature's stored name changed.
Function MGHPersistIdentity(h As Inventor.HoleFeature, g As OutputGroup, _
    allHoles As Inventor.HoleFeatures, def As Inventor.PartComponentDefinition, _
    sketch As Inventor.PlanarSketch, warnings As System.Collections.Generic.List(Of String)) As Boolean
    Dim previousLabel As String = ""
    If h.AttributeSets.NameIsUsed("MGH_Generator") Then
        Dim previous As MGHParsedKey = MGHReadIdentity(h.AttributeSets.Item("MGH_Generator"))
        If previous IsNot Nothing Then previousLabel = previous.Label
    End If
    Dim aset As Inventor.AttributeSet = MGHIdentitySet(h)
    MGHWriteIdentityFields(aset, g)
    Dim labelChanged As Boolean = previousLabel <> "" AndAlso _
        Not String.Equals(previousLabel, g.Label, System.StringComparison.Ordinal)
    If previousLabel = "" OrElse labelChanged Then
        Dim specificationTag As String = If(g.Mode = "Threaded", g.ThreadDesignation, _
            "D" & g.DiameterIn.ToString("0.0000", System.Globalization.CultureInfo.InvariantCulture))
        Try
            h.Name = UniqueHoleName(allHoles, "MGH - " & CleanName(g.Label) & " - " & specificationTag, h)
        Catch renameEx As System.Exception
            warnings.Add("Hole feature for '" & g.Label & "' kept its Inventor default name (" & renameEx.Message & ").")
        End Try
        If sketch IsNot Nothing Then
            Try
                sketch.Name = UniqueSketchName(def, "MGH Sketch - " & CleanName(g.Label) & " - " & specificationTag, sketch)
            Catch renameEx As System.Exception
                warnings.Add("Sketch for '" & g.Label & "' kept its Inventor default name (" & renameEx.Message & ").")
            End Try
        End If
    End If
    Return labelChanged
End Function

Function MGHDefaultHardwareLibrary() As String
    Return "C:\Users\dblack\Desktop\ODINN\Design Activity\Hardware"
End Function

' Folder names under the hardware library. A size such as 1/4 cannot be a Windows
' folder name, so the hyphenated form is tried first.
Function MGHSizeFolderNames(size As String) As String()
    Dim names As New System.Collections.Generic.List(Of String)()
    If size Is Nothing Then Return names.ToArray()
    Dim trimmed As String = size.Trim()
    If trimmed = "" OrElse String.Equals(trimmed, "Custom", System.StringComparison.OrdinalIgnoreCase) Then
        Return names.ToArray()
    End If
    If trimmed.IndexOf("/"c) >= 0 OrElse trimmed.IndexOf("\"c) >= 0 Then
        names.Add(trimmed.Replace("/"c, "-"c).Replace("\"c, "-"c))
        names.Add(trimmed.Replace("/"c, "_"c).Replace("\"c, "_"c))
        Dim slash As Integer = trimmed.IndexOf("/"c)
        If slash < 0 Then slash = trimmed.IndexOf("\"c)
        Dim numerator As Double = 0
        Dim denominator As Double = 0
        If slash > 0 AndAlso slash < trimmed.Length - 1 AndAlso _
           Double.TryParse(trimmed.Substring(0, slash), System.Globalization.NumberStyles.Float, System.Globalization.CultureInfo.InvariantCulture, numerator) AndAlso _
           Double.TryParse(trimmed.Substring(slash + 1), System.Globalization.NumberStyles.Float, System.Globalization.CultureInfo.InvariantCulture, denominator) AndAlso _
           denominator <> 0 Then
            names.Add((numerator / denominator).ToString("0.000", System.Globalization.CultureInfo.InvariantCulture))
        End If
    Else
        names.Add(trimmed)
    End If
    Return names.ToArray()
End Function

' "0.500Lg" is a half-inch screw folder. Returns inches, or -1 when the name is not a length.
Function MGHParseLengthFolder(name As String) As Double
    If name Is Nothing Then Return -1
    Dim text As String = name.Trim()
    If text.Length < 3 Then Return -1
    If Not text.EndsWith("Lg", System.StringComparison.OrdinalIgnoreCase) Then Return -1
    text = text.Substring(0, text.Length - 2).Trim()
    Dim inches As Double = 0
    If Not Double.TryParse(text, System.Globalization.NumberStyles.Float, System.Globalization.CultureInfo.InvariantCulture, inches) Then Return -1
    If inches <= 0 Then Return -1
    Return inches
End Function

' Shortest folder that is at least the required length. The longest folder when all are short.
' tooShort is true when every folder is shorter than required. Empty when none are length folders.
Function MGHBestLengthFolder(names() As String, requiredInches As Double, ByRef tooShort As Boolean) As String
    tooShort = False
    If names Is Nothing OrElse names.Length = 0 Then Return ""
    Dim bestName As String = ""
    Dim bestLength As Double = 0
    Dim longestName As String = ""
    Dim longest As Double = -1
    Dim i As Integer
    For i = 0 To names.Length - 1
        Dim length As Double = MGHParseLengthFolder(names(i))
        If length < 0 Then Continue For
        If length > longest Then
            longest = length
            longestName = names(i)
        End If
        If length + 0.002 >= requiredInches AndAlso (bestName = "" OrElse length < bestLength) Then
            bestName = names(i)
            bestLength = length
        End If
    Next
    If bestName <> "" Then Return bestName
    tooShort = longestName <> ""
    Return longestName
End Function

' Inches of screw needed under the head: the joint span, each washer, and the nut.
Function MGHStackLengthInches(gripCm As Double, washerCm As Double, washerCount As Integer, nutCm As Double, nutCount As Integer) As Double
    If gripCm < 0 Then gripCm = 0
    If washerCm < 0 OrElse washerCount < 0 Then
        washerCm = 0
        washerCount = 0
    End If
    If nutCm < 0 OrElse nutCount < 0 Then
        nutCm = 0
        nutCount = 0
    End If
    Return (gripCm + washerCm * washerCount + nutCm * nutCount) / 2.54
End Function

Function MGHFormatInches(inches As Double) As String
    Return inches.ToString("0.000", System.Globalization.CultureInfo.InvariantCulture)
End Function

' Holes of one size that need the same thousandth of an inch share one screw file.
Function MGHScrewLengthKey(sizeName As String, requiredInches As Double) As String
    If sizeName Is Nothing Then sizeName = ""
    If requiredInches < 0 Then requiredInches = 0
    Return sizeName.Trim() & "|" & MGHFormatInches(requiredInches)
End Function

' Washer and nut thicknesses are centimeters. The returned allowances are inches.
Sub MGHScrewAllowances(washerCm As Double, nutCm As Double, underScrew As Boolean, underNut As Boolean, includeNut As Boolean, _
    ByRef screwWasherIn As Double, ByRef nutWasherIn As Double, ByRef nutIn As Double)
    screwWasherIn = 0
    nutWasherIn = 0
    nutIn = 0
    If washerCm > 0 AndAlso underScrew Then screwWasherIn = washerCm / 2.54
    If washerCm > 0 AndAlso underNut Then nutWasherIn = washerCm / 2.54
    If nutCm > 0 AndAlso includeNut Then nutIn = nutCm / 2.54
End Sub

' Grip is centimeters. Allowances are inches. The result is inches under the head.
Function MGHScrewRequiredInches(gripCm As Double, screwWasherIn As Double, nutWasherIn As Double, nutIn As Double) As Double
    Dim gripIn As Double = 0
    If gripCm > 0 Then gripIn = gripCm / 2.54
    If screwWasherIn < 0 Then screwWasherIn = 0
    If nutWasherIn < 0 Then nutWasherIn = 0
    If nutIn < 0 Then nutIn = 0
    Dim required As Double = gripIn + screwWasherIn + nutWasherIn + nutIn
    If required < 0 Then required = 0
    Return required
End Function

' Shown before the screw file window. Lengths are inches under the head.
Function MGHScrewLengthMessage(sizeName As String, gripIn As Double, screwWasherIn As Double, nutWasherIn As Double, nutIn As Double, _
    folderName As String, tooShort As Boolean, holeCount As Integer, groupText As String) As String
    If gripIn < 0 Then gripIn = 0
    If screwWasherIn < 0 Then screwWasherIn = 0
    If nutWasherIn < 0 Then nutWasherIn = 0
    If nutIn < 0 Then nutIn = 0
    Dim required As Double = gripIn + screwWasherIn + nutWasherIn + nutIn
    Dim text As String = "Select a " & sizeName & " screw at least " & MGHFormatInches(required) & " in under the head." & vbCrLf
    If holeCount > 0 Then
        text &= "This length is for " & holeCount.ToString() & " hole"
        If holeCount <> 1 Then text &= "s"
        If groupText IsNot Nothing AndAlso groupText <> "" Then text &= " in " & groupText
        text &= "." & vbCrLf
    End If
    text &= vbCrLf & "Distance from the hole rim to the plate face: " & MGHFormatInches(gripIn) & " in" & vbCrLf
    If screwWasherIn > 0 Then text &= "Washer under the screw: " & MGHFormatInches(screwWasherIn) & " in" & vbCrLf
    If nutWasherIn > 0 Then text &= "Washer under the nut: " & MGHFormatInches(nutWasherIn) & " in" & vbCrLf
    If nutIn > 0 Then text &= "Nut: " & MGHFormatInches(nutIn) & " in" & vbCrLf
    text &= vbCrLf
    If tooShort AndAlso folderName <> "" Then
        text &= "No length folder is at least that long. The window will open " & folderName & ", the longest folder." & vbCrLf
    ElseIf folderName <> "" Then
        text &= "Click OK, then select a screw from " & folderName & "." & vbCrLf
    Else
        text &= "Click OK, then select a screw at least that long." & vbCrLf
    End If
    text &= "Click Cancel to skip the screw."
    Return text
End Function

Function MGHPreferredRoleDirectory(library As String, size As String, role As String) As String
    Dim names() As String = MGHSizeFolderNames(size)
    If names.Length = 0 OrElse library Is Nothing OrElse library.Trim() = "" Then Return ""
    Return System.IO.Path.Combine(library.Trim(), names(0), role)
End Function

' The first candidate directory that already exists, or empty when none do.
Function MGHResolveRoleDirectory(library As String, size As String, role As String) As String
    If library Is Nothing OrElse library.Trim() = "" Then Return ""
    Dim root As String = library.Trim()
    Dim names() As String = MGHSizeFolderNames(size)
    Dim i As Integer
    For i = 0 To names.Length - 1
        Dim candidate As String = System.IO.Path.Combine(root, names(i), role)
        If System.IO.Directory.Exists(candidate) Then Return candidate
    Next
    Return ""
End Function

' True when the higher end along the washer axis is the face that sits on the plate.
' A toothed end has many more faces and is seated against the plate. When the two
' ends match, either face is acceptable and the broader flat face is used.
Function MGHWasherBearingIsHighEnd(lowFaces As Integer, highFaces As Integer, lowArea As Double, highArea As Double) As Boolean
    Dim lowToothed As Boolean = lowFaces >= highFaces * 2 AndAlso lowFaces >= highFaces + 4
    Dim highToothed As Boolean = highFaces >= lowFaces * 2 AndAlso highFaces >= lowFaces + 4
    If highToothed AndAlso Not lowToothed Then Return True
    If lowToothed AndAlso Not highToothed Then Return False
    If highArea > lowArea + 0.0000001 Then Return True
    Return False
End Function

Sub MGHCross(ax As Double, ay As Double, az As Double, bx As Double, by As Double, bz As Double, _
    ByRef cx As Double, ByRef cy As Double, ByRef cz As Double)
    cx = ay * bz - az * by
    cy = az * bx - ax * bz
    cz = ax * by - ay * bx
End Sub

Function MGHNormalize(ByRef x As Double, ByRef y As Double, ByRef z As Double) As Boolean
    Dim mag As Double = System.Math.Sqrt(x * x + y * y + z * z)
    If mag < 0.000000001 Then Return False
    x /= mag : y /= mag : z /= mag
    Return True
End Function

' Right-handed X and Y for a unit Z axis. Spin around Z is fixed so a re-run lands the same way.
Sub MGHWasherBasis(zx As Double, zy As Double, zz As Double, _
    ByRef xx As Double, ByRef xy As Double, ByRef xz As Double, _
    ByRef yx As Double, ByRef yy As Double, ByRef yz As Double)
    Dim rx As Double, ry As Double, rz As Double
    If System.Math.Abs(zx) < 0.9 Then
        rx = 1 : ry = 0 : rz = 0
    Else
        rx = 0 : ry = 1 : rz = 0
    End If
    MGHCross(zx, zy, zz, rx, ry, rz, xx, xy, xz)
    If Not MGHNormalize(xx, xy, xz) Then Throw New System.Exception("Could not build a washer axis.")
    MGHCross(zx, zy, zz, xx, xy, xz, yx, yy, yz)
    If Not MGHNormalize(yx, yy, yz) Then Throw New System.Exception("Could not build a washer axis.")
End Sub

' Maps a part-space point into the assembly. The bearing point lands on the contact
' point, and the washer axis (from the plate face through the washer) follows the outward normal.
Sub MGHMapWasherPoint(bX As Double, bY As Double, bZ As Double, aX As Double, aY As Double, aZ As Double, _
    cX As Double, cY As Double, cZ As Double, nX As Double, nY As Double, nZ As Double, _
    pX As Double, pY As Double, pZ As Double, ByRef oX As Double, ByRef oY As Double, ByRef oZ As Double)
    Dim fxx As Double, fxy As Double, fxz As Double, fyx As Double, fyy As Double, fyz As Double
    Dim txx As Double, txy As Double, txz As Double, tyx As Double, tyy As Double, tyz As Double
    MGHWasherBasis(aX, aY, aZ, fxx, fxy, fxz, fyx, fyy, fyz)
    MGHWasherBasis(nX, nY, nZ, txx, txy, txz, tyx, tyy, tyz)
    Dim dx As Double = pX - bX
    Dim dy As Double = pY - bY
    Dim dz As Double = pZ - bZ
    Dim alongX As Double = dx * fxx + dy * fxy + dz * fxz
    Dim alongY As Double = dx * fyx + dy * fyy + dz * fyz
    Dim alongZ As Double = dx * aX + dy * aY + dz * aZ
    oX = cX + alongX * txx + alongY * tyx + alongZ * nX
    oY = cY + alongX * txy + alongY * tyy + alongZ * nY
    oZ = cZ + alongX * txz + alongY * tyz + alongZ * nZ
End Sub

Public Class MGHWasherModel
    Public BearingX As Double
    Public BearingY As Double
    Public BearingZ As Double
    Public AxisX As Double
    Public AxisY As Double
    Public AxisZ As Double
    Public MidX As Double
    Public MidY As Double
    Public MidZ As Double
    Public Thickness As Double
    Public InnerRadius As Double
    Public BearingEdge As Inventor.Edge
    Public Part As Inventor.PartDocument
    Public FilePath As String
End Class

' One component-hole walk is reused for the washer, the nut, and the screw.
Public Class MGHSeatCacheEntry
    Public Ok As Boolean
    Public Contact As Inventor.Point
    Public Outward As Inventor.UnitVector
    Public HoleEdge As Inventor.Edge
End Class

' Hardware already in the assembly, read once before placement starts.
Public Class MGHKnownHardware
    Public Occurrence As Inventor.ComponentOccurrence
    Public Role As String
    Public Side As String
    Public HasSide As Boolean
    Public Center As Inventor.Point
    Public FromAttribute As Boolean
    Public Name As String
End Class

' Assembly attribute sets reject CopyWithOwner on some files. Try both flags.
Function MGHEnsureAttributeSet(sets As Inventor.AttributeSets, name As String) As Inventor.AttributeSet
    If sets.NameIsUsed(name) Then Return sets.Item(name)
    Try
        Return sets.Add(name, False)
    Catch
    End Try
    Return sets.Add(name, True)
End Function

Function MGHReadHardwareLibrary(doc As Inventor.Document) As String
    Try
        If doc Is Nothing OrElse Not doc.AttributeSets.NameIsUsed("MGH_Settings") Then Return ""
        Return MGHGetAttr(doc.AttributeSets.Item("MGH_Settings"), "HardwareLibrary")
    Catch
        Return ""
    End Try
End Function

Sub MGHWriteHardwareLibrary(doc As Inventor.Document, path As String)
    If doc Is Nothing OrElse path Is Nothing Then Return
    If path.Length = 0 OrElse path.Length > 255 Then Return
    Dim aset As Inventor.AttributeSet = MGHEnsureAttributeSet(doc.AttributeSets, "MGH_Settings")
    MGHPutAttr(aset, "HardwareLibrary", path)
End Sub

Function MGHIsUserCancel(ex As System.Exception) As Boolean
    If ex Is Nothing Then Return False
    If ex.HResult = &H80004004 Then Return True
    If ex.Message Is Nothing Then Return False
    Return ex.Message.IndexOf("80004004", System.StringComparison.OrdinalIgnoreCase) >= 0
End Function

Function MGHPickPartFile(app As Inventor.Application, title As String, initialDirectory As String) As String
    Dim folder As String = ""
    If initialDirectory <> "" AndAlso System.IO.Directory.Exists(initialDirectory) Then folder = initialDirectory
    Try
        Dim dialog As Inventor.FileDialog = Nothing
        app.CreateFileDialog(dialog)
        dialog.Filter = "Inventor Parts (*.ipt)|*.ipt"
        dialog.DialogTitle = title
        dialog.CancelError = True
        Try
            dialog.InsertMode = False
        Catch
        End Try
        If folder <> "" Then dialog.InitialDirectory = folder
        dialog.ShowOpen()
        If dialog.FileName Is Nothing Then Return ""
        Dim selected As String = dialog.FileName.Trim()
        If selected <> "" AndAlso System.IO.File.Exists(selected) Then Return selected
        Return ""
    Catch ex As System.Exception
        If MGHIsUserCancel(ex) Then Return ""
    End Try
    ' Inventor's file dialog raises E_FAIL for some option combinations.
    ' The standard window still opens in the Washers folder.
    Dim browser As New System.Windows.Forms.OpenFileDialog()
    browser.Title = title
    browser.Filter = "Inventor parts (*.ipt)|*.ipt"
    browser.CheckFileExists = True
    browser.RestoreDirectory = True
    If folder <> "" Then
        browser.InitialDirectory = folder
        browser.FileName = folder & System.IO.Path.DirectorySeparatorChar
    End If
    Dim picked As String = ""
    If browser.ShowDialog() = System.Windows.Forms.DialogResult.OK Then picked = browser.FileName
    browser.Dispose()
    Return picked
End Function

Function MGHBrowseHardwareLibrary(currentPath As String) As String
    Dim browser As New System.Windows.Forms.FolderBrowserDialog()
    browser.Description = "Select the hardware folder. Each size folder, such as #8, should contain a Washers folder."
    browser.ShowNewFolderButton = False
    If currentPath <> "" AndAlso System.IO.Directory.Exists(currentPath) Then browser.SelectedPath = currentPath
    Dim chosen As String = ""
    If browser.ShowDialog() = System.Windows.Forms.DialogResult.OK Then chosen = browser.SelectedPath
    browser.Dispose()
    Return chosen
End Function

Function MGHCircularEdge(edge As Inventor.Edge, ByRef center As Inventor.Point, ByRef radius As Double) As Boolean
    center = Nothing
    radius = 0
    If edge Is Nothing Then Return False
    Try
        Dim circ As Inventor.Circle = TryCast(edge.Geometry, Inventor.Circle)
        If circ IsNot Nothing Then
            center = circ.Center
            radius = circ.Radius
            Return radius > 0
        End If
        Dim arc As Inventor.Arc3d = TryCast(edge.Geometry, Inventor.Arc3d)
        If arc IsNot Nothing Then
            center = arc.Center
            radius = arc.Radius
            Return radius > 0
        End If
    Catch
        Return False
    End Try
    Return False
End Function

Function MGHDistanceToAxis(px As Double, py As Double, pz As Double, ax As Double, ay As Double, az As Double, _
    dx As Double, dy As Double, dz As Double) As Double
    Dim vx As Double = px - ax
    Dim vy As Double = py - ay
    Dim vz As Double = pz - az
    Dim cx As Double, cy As Double, cz As Double
    MGHCross(vx, vy, vz, dx, dy, dz, cx, cy, cz)
    Return System.Math.Sqrt(cx * cx + cy * cy + cz * cz)
End Function

' Index of the other end of the selected hole, or -1. A matching radius wins.
' Otherwise the farthest rim on the axis that is not larger than the selected hole.
Function MGHChooseOppositeRim(selX As Double, selY As Double, selZ As Double, _
    axisX As Double, axisY As Double, axisZ As Double, selRadius As Double, _
    candidates As System.Collections.Generic.List(Of MGHRimCandidate)) As Integer
    Dim sameSize As Integer = MGHFarthestRim(selX, selY, selZ, axisX, axisY, axisZ, selRadius, candidates, True)
    If sameSize >= 0 Then Return sameSize
    Return MGHFarthestRim(selX, selY, selZ, axisX, axisY, axisZ, selRadius, candidates, False)
End Function

Function MGHFarthestRim(selX As Double, selY As Double, selZ As Double, _
    axisX As Double, axisY As Double, axisZ As Double, selRadius As Double, _
    candidates As System.Collections.Generic.List(Of MGHRimCandidate), sameRadius As Boolean) As Integer
    If candidates Is Nothing Then Return -1
    Dim best As Integer = -1
    Dim bestDist As Double = 0
    Dim i As Integer
    For i = 0 To candidates.Count - 1
        Dim c As MGHRimCandidate = candidates(i)
        If c Is Nothing Then Continue For
        If MGHDistanceToAxis(c.X, c.Y, c.Z, selX, selY, selZ, axisX, axisY, axisZ) > 0.05 Then Continue For
        Dim dx As Double = c.X - selX
        Dim dy As Double = c.Y - selY
        Dim dz As Double = c.Z - selZ
        Dim dist As Double = System.Math.Sqrt(dx * dx + dy * dy + dz * dz)
        If dist < 0.02 Then Continue For
        If sameRadius Then
            If System.Math.Abs(c.Radius - selRadius) > System.Math.Max(0.05, selRadius * 0.2) Then Continue For
        ElseIf c.Radius > selRadius * 1.05 OrElse c.Radius <= 0.02 Then
            Continue For
        End If
        If best < 0 OrElse dist > bestDist + 0.0000001 Then
            best = i
            bestDist = dist
        End If
    Next
    Return best
End Function

' A chamfer or countersink can be the opening the washer sits on, so the far rim may be larger than the hole.
Function MGHChainRadiusOk(radius As Double, selRadius As Double) As Boolean
    If radius <= 0.02 OrElse selRadius <= 0 Then Return False
    If radius < selRadius * 0.35 Then Return False
    If radius > selRadius * 4.0 + 0.05 Then Return False
    Return True
End Function

' Farthest coaxial rim in the chamfer band. -1 when none qualifies.
Function MGHChooseChainExit(selX As Double, selY As Double, selZ As Double, _
    axisX As Double, axisY As Double, axisZ As Double, selRadius As Double, _
    candidates As System.Collections.Generic.List(Of MGHRimCandidate)) As Integer
    If candidates Is Nothing Then Return -1
    Dim axisTol As Double = System.Math.Max(0.1, selRadius * 0.35)
    Dim best As Integer = -1
    Dim bestDist As Double = 0
    Dim i As Integer
    For i = 0 To candidates.Count - 1
        Dim c As MGHRimCandidate = candidates(i)
        If c Is Nothing Then Continue For
        If Not MGHChainRadiusOk(c.Radius, selRadius) Then Continue For
        If MGHDistanceToAxis(c.X, c.Y, c.Z, selX, selY, selZ, axisX, axisY, axisZ) > axisTol Then Continue For
        Dim dx As Double = c.X - selX
        Dim dy As Double = c.Y - selY
        Dim dz As Double = c.Z - selZ
        Dim dist As Double = System.Math.Sqrt(dx * dx + dy * dy + dz * dz)
        If dist < 0.02 Then Continue For
        If best < 0 OrElse dist > bestDist + 0.0000001 Then
            best = i
            bestDist = dist
        End If
    Next
    Return best
End Function

' Thickness between the first two ray hits, or -1 when the hits are not a through hole.
Function MGHExitThickness(firstDist As Double, secondDist As Double) As Double
    If firstDist < -0.001 OrElse secondDist < firstDist + 0.02 Then Return -1
    If secondDist - firstDist > 15 Then Return -1
    Return secondDist - firstDist
End Function

' Parameter t where point + t * direction meets the plane. NaN when the line is parallel to the plane.
Function MGHLinePlaneT(dirX As Double, dirY As Double, dirZ As Double, _
    px As Double, py As Double, pz As Double, _
    nx As Double, ny As Double, nz As Double, _
    qx As Double, qy As Double, qz As Double) As Double
    Dim denom As Double = nx * dirX + ny * dirY + nz * dirZ
    If System.Math.Abs(denom) < 0.000000001 Then Return System.Double.NaN
    Return ((qx - px) * nx + (qy - py) * ny + (qz - pz) * nz) / denom
End Function

' Assembly point of the far rim. rotatedDx/Dy/Dz is the part-space vector from the
' clicked center to the far center after the occurrence rotation. The proxy circle
' normal is not used: Inventor often flips it, which put both washers on the clicked rim.
Sub MGHFarRimPoint(selX As Double, selY As Double, selZ As Double, _
    rotatedDx As Double, rotatedDy As Double, rotatedDz As Double, _
    ByRef farX As Double, ByRef farY As Double, ByRef farZ As Double)
    farX = selX + rotatedDx
    farY = selY + rotatedDy
    farZ = selZ + rotatedDz
End Sub

' atSelected points out of the hole at the clicked rim. Otherwise it points out at the far rim.
Sub MGHOutwardFromEnds(selX As Double, selY As Double, selZ As Double, _
    otherX As Double, otherY As Double, otherZ As Double, atSelected As Boolean, _
    ByRef ox As Double, ByRef oy As Double, ByRef oz As Double)
    If atSelected Then
        ox = selX - otherX : oy = selY - otherY : oz = selZ - otherZ
    Else
        ox = otherX - selX : oy = otherY - selY : oz = otherZ - selZ
    End If
    Dim length As Double = System.Math.Sqrt(ox * ox + oy * oy + oz * oz)
    If length < 0.000000001 Then
        ox = 0 : oy = 0 : oz = 0
    Else
        ox /= length : oy /= length : oz /= length
    End If
End Sub

' Outward unit vector of a planar face, pointing out of the solid.
Function MGHFaceOutward(face As Inventor.Face, body As Inventor.SurfaceBody, app As Inventor.Application) As Inventor.UnitVector
    Dim pl As Inventor.Plane = TryCast(face.Geometry, Inventor.Plane)
    If pl Is Nothing OrElse body Is Nothing Then Throw New System.Exception("The selected plate face is no longer planar.")
    Dim n As Inventor.UnitVector = pl.Normal
    Dim p As Inventor.Point = face.PointOnFace
    Dim offset As Double = 0.02
    Dim plus() As Double = {p.X + n.X * offset, p.Y + n.Y * offset, p.Z + n.Z * offset}
    Dim minus() As Double = {p.X - n.X * offset, p.Y - n.Y * offset, p.Z - n.Z * offset}
    Dim plusInside As Boolean = (body.IsPointInside(plus, False) = Inventor.ContainmentEnum.kInsideContainment)
    Dim minusInside As Boolean = (body.IsPointInside(minus, False) = Inventor.ContainmentEnum.kInsideContainment)
    Dim tg As Inventor.TransientGeometry = app.TransientGeometry
    If minusInside AndAlso Not plusInside Then Return n
    If plusInside AndAlso Not minusInside Then Return tg.CreateUnitVector(-n.X, -n.Y, -n.Z)
    If face.IsParamReversed Then Return tg.CreateUnitVector(-n.X, -n.Y, -n.Z)
    Return n
End Function

Function MGHReadWasher(app As Inventor.Application, path As String) As MGHWasherModel
    Dim opened As Inventor.Document = app.Documents.Open(path, False)
    Dim part As Inventor.PartDocument = TryCast(opened, Inventor.PartDocument)
    If part Is Nothing Then Throw New System.Exception("The selected file is not an Inventor part: " & path)
    Dim body As Inventor.SurfaceBody = Nothing
    Dim bestVolume As Double = -1
    For Each candidate As Inventor.SurfaceBody In part.ComponentDefinition.SurfaceBodies
        If Not candidate.IsSolid Then Continue For
        Dim volume As Double = 0
        Try
            volume = candidate.Volume(1.0)
        Catch
            volume = 0
        End Try
        If body Is Nothing OrElse volume > bestVolume Then
            body = candidate
            bestVolume = volume
        End If
    Next
    If body Is Nothing Then Throw New System.Exception("The washer part has no solid body: " & System.IO.Path.GetFileName(path))

    Dim holeFace As Inventor.Face = Nothing
    Dim holeRadius As Double = 0
    Dim axisPoint As Inventor.Point = Nothing
    Dim axisDir As Inventor.UnitVector = Nothing
    For Each f As Inventor.Face In body.Faces
        Dim cyl As Inventor.Cylinder = TryCast(f.Geometry, Inventor.Cylinder)
        If cyl Is Nothing Then Continue For
        If cyl.Radius < 0.04 OrElse cyl.Radius > 3.0 Then Continue For
        If holeFace Is Nothing OrElse cyl.Radius < holeRadius Then
            holeFace = f
            holeRadius = cyl.Radius
            axisPoint = cyl.BasePoint
            axisDir = cyl.AxisVector
        End If
    Next
    If holeFace Is Nothing Then Throw New System.Exception("Could not find the hole through " & System.IO.Path.GetFileName(path) & ". A washer needs one cylindrical hole.")

    Dim lowT As Double = 0
    Dim highT As Double = 0
    Dim haveEnd As Boolean = False
    Dim lowArea As Double = 0
    Dim highArea As Double = 0
    For Each f As Inventor.Face In body.Faces
        Dim pl As Inventor.Plane = TryCast(f.Geometry, Inventor.Plane)
        If pl Is Nothing Then Continue For
        If System.Math.Abs(pl.Normal.DotProduct(axisDir)) < 0.98 Then Continue For
        Dim sample As Inventor.Point = f.PointOnFace
        Dim t As Double = (sample.X - axisPoint.X) * axisDir.X + (sample.Y - axisPoint.Y) * axisDir.Y + (sample.Z - axisPoint.Z) * axisDir.Z
        Dim area As Double = 0
        Try
            area = f.Evaluator.Area
        Catch
            area = 0
        End Try
        If Not haveEnd Then
            lowT = t : highT = t : lowArea = area : highArea = area : haveEnd = True
        ElseIf t < lowT - 0.002 Then
            lowT = t : lowArea = area
        ElseIf t > highT + 0.002 Then
            highT = t : highArea = area
        ElseIf System.Math.Abs(t - lowT) <= System.Math.Abs(t - highT) Then
            lowArea += area
        Else
            highArea += area
        End If
    Next
    If Not haveEnd OrElse highT - lowT < 0.002 Then
        Throw New System.Exception("Could not find the two faces of " & System.IO.Path.GetFileName(path) & ".")
    End If

    Dim band As Double = System.Math.Max(0.03, (highT - lowT) * 0.35)
    Dim lowFaces As Integer = 0
    Dim highFaces As Integer = 0
    For Each f As Inventor.Face In body.Faces
        Dim sample As Inventor.Point = Nothing
        Try
            sample = f.PointOnFace
        Catch
            sample = Nothing
        End Try
        If sample Is Nothing Then Continue For
        Dim t As Double = (sample.X - axisPoint.X) * axisDir.X + (sample.Y - axisPoint.Y) * axisDir.Y + (sample.Z - axisPoint.Z) * axisDir.Z
        If System.Math.Abs(t - lowT) <= band Then lowFaces += 1
        If System.Math.Abs(t - highT) <= band Then highFaces += 1
    Next
    Dim bearingT As Double = lowT
    Dim axisSign As Double = 1
    If MGHWasherBearingIsHighEnd(lowFaces, highFaces, lowArea, highArea) Then
        bearingT = highT
        axisSign = -1
    End If

    Dim bearingEdge As Inventor.Edge = Nothing
    Dim bearingGap As Double = 0
    Dim haveEdge As Boolean = False
    For Each f As Inventor.Face In body.Faces
        For Each e As Inventor.Edge In f.Edges
            Dim edgeCenter As Inventor.Point = Nothing
            Dim radius As Double = 0
            If Not MGHCircularEdge(e, edgeCenter, radius) Then Continue For
            If System.Math.Abs(radius - holeRadius) > System.Math.Max(0.05, holeRadius * 0.25) Then Continue For
            Dim radial As Double = MGHDistanceToAxis(edgeCenter.X, edgeCenter.Y, edgeCenter.Z, _
                axisPoint.X, axisPoint.Y, axisPoint.Z, axisDir.X, axisDir.Y, axisDir.Z)
            If radial > 0.05 Then Continue For
            Dim t As Double = (edgeCenter.X - axisPoint.X) * axisDir.X + (edgeCenter.Y - axisPoint.Y) * axisDir.Y + (edgeCenter.Z - axisPoint.Z) * axisDir.Z
            Dim gap As Double = System.Math.Abs(t - bearingT)
            If Not haveEdge OrElse gap < bearingGap Then
                bearingEdge = e
                bearingGap = gap
                haveEdge = True
            End If
        Next
    Next

    Dim model As New MGHWasherModel()
    model.Part = part
    model.InnerRadius = holeRadius
    model.Thickness = highT - lowT
    model.BearingX = axisPoint.X + axisDir.X * bearingT
    model.BearingY = axisPoint.Y + axisDir.Y * bearingT
    model.BearingZ = axisPoint.Z + axisDir.Z * bearingT
    model.AxisX = axisDir.X * axisSign
    model.AxisY = axisDir.Y * axisSign
    model.AxisZ = axisDir.Z * axisSign
    model.MidX = model.BearingX + model.AxisX * model.Thickness / 2.0
    model.MidY = model.BearingY + model.AxisY * model.Thickness / 2.0
    model.MidZ = model.BearingZ + model.AxisZ * model.Thickness / 2.0
    model.BearingEdge = bearingEdge
    model.FilePath = path
    Return model
End Function

Function MGHCustomProperties(doc As Inventor.Document) As Inventor.PropertySet
    Return doc.PropertySets.Item("{D5CDD505-2E9C-101B-9397-08002B2CF9AE}")
End Function

Function MGHReadCustomProperty(doc As Inventor.Document, propName As String) As String
    Try
        Dim prop As Inventor.Property = MGHCustomProperties(doc).Item(propName)
        If prop Is Nothing OrElse prop.Value Is Nothing Then Return ""
        Return System.Convert.ToString(prop.Value)
    Catch
        Return ""
    End Try
End Function

Sub MGHWriteCustomProperty(doc As Inventor.Document, propName As String, propValue As String)
    Dim props As Inventor.PropertySet = MGHCustomProperties(doc)
    Dim existing As Inventor.Property = Nothing
    Try
        existing = props.Item(propName)
    Catch
        existing = Nothing
    End Try
    If existing Is Nothing Then
        props.Add(propValue, propName, System.Reflection.Missing.Value)
    Else
        existing.Value = propValue
    End If
End Sub

' The saved face is the one that sits against the washer. Nothing when it has not been chosen or no longer binds.
Function MGHLoadMountingFace(part As Inventor.PartDocument) As Inventor.Face
    Dim keyText As String = MGHReadCustomProperty(part, "MGH Mounting Face")
    Dim contextText As String = MGHReadCustomProperty(part, "MGH Mounting Face Context")
    If keyText = "" OrElse contextText = "" Then Return Nothing
    Dim ctxData() As Byte = System.Convert.FromBase64String(contextText)
    Dim ctx As Integer = part.ReferenceKeyManager.LoadContextFromArray(ctxData)
    Try
        Dim key() As Byte = New Byte() {}
        part.ReferenceKeyManager.StringToKey(keyText, key)
        Dim matchType As Object = Nothing
        Dim bound As Object = part.ReferenceKeyManager.BindKeyToObject(key, ctx, matchType)
        Dim face As Inventor.Face = TryCast(bound, Inventor.Face)
        If face Is Nothing Then
            Dim many As Inventor.ObjectCollection = TryCast(bound, Inventor.ObjectCollection)
            If many IsNot Nothing AndAlso many.Count > 0 Then face = TryCast(many.Item(1), Inventor.Face)
        End If
        Return face
    Finally
        Try
            part.ReferenceKeyManager.ReleaseKeyContext(ctx)
        Catch
        End Try
    End Try
End Function

Sub MGHSaveMountingFace(part As Inventor.PartDocument, face As Inventor.Face)
    Dim ctx As Integer = part.ReferenceKeyManager.CreateKeyContext()
    Try
        Dim key() As Byte = New Byte() {}
        face.GetReferenceKey(key, ctx)
        Dim ctxData() As Byte = New Byte() {}
        part.ReferenceKeyManager.SaveContextToArray(ctx, ctxData)
        MGHWriteCustomProperty(part, "MGH Mounting Face", part.ReferenceKeyManager.KeyToString(key))
        MGHWriteCustomProperty(part, "MGH Mounting Face Context", System.Convert.ToBase64String(ctxData))
    Finally
        Try
            part.ReferenceKeyManager.ReleaseKeyContext(ctx)
        Catch
        End Try
    End Try
End Sub

' Point the nut so the chosen face is the contact and the body extends away from that face.
Sub MGHSetBearingFromFace(model As MGHWasherModel, face As Inventor.Face, app As Inventor.Application)
    If model Is Nothing OrElse face Is Nothing Then Throw New System.Exception("the mounting face is missing")
    Dim pl As Inventor.Plane = TryCast(face.Geometry, Inventor.Plane)
    If pl Is Nothing Then Throw New System.Exception("Click the flat face that sits against the washer.")
    Dim dirX As Double = model.AxisX
    Dim dirY As Double = model.AxisY
    Dim dirZ As Double = model.AxisZ
    If Not MGHNormalize(dirX, dirY, dirZ) Then Throw New System.Exception("the nut hole has no axis")
    If System.Math.Abs(pl.Normal.X * dirX + pl.Normal.Y * dirY + pl.Normal.Z * dirZ) < 0.95 Then
        Throw New System.Exception("That face is not perpendicular to the nut hole. Click the flat face around the hole.")
    End If
    Dim t As Double = MGHLinePlaneT(dirX, dirY, dirZ, model.BearingX, model.BearingY, model.BearingZ, _
        pl.Normal.X, pl.Normal.Y, pl.Normal.Z, pl.RootPoint.X, pl.RootPoint.Y, pl.RootPoint.Z)
    If System.Double.IsNaN(t) Then Throw New System.Exception("That face does not cross the nut hole.")
    If System.Math.Abs(t) > 0.2 AndAlso System.Math.Abs(System.Math.Abs(t) - model.Thickness) > 0.2 Then
        Throw New System.Exception("That face is not an end of the nut. Click the flat face around the hole.")
    End If
    model.BearingX = model.BearingX + dirX * t
    model.BearingY = model.BearingY + dirY * t
    model.BearingZ = model.BearingZ + dirZ * t
    Dim body As Inventor.SurfaceBody = face.SurfaceBody
    Dim faceOut As Inventor.UnitVector = MGHFaceOutward(face, body, app)
    model.AxisX = -faceOut.X
    model.AxisY = -faceOut.Y
    model.AxisZ = -faceOut.Z
    Dim rx As Double, ry As Double, rz As Double
    If System.Math.Abs(model.AxisX) < 0.9 Then
        MGHCross(model.AxisX, model.AxisY, model.AxisZ, 1, 0, 0, rx, ry, rz)
    Else
        MGHCross(model.AxisX, model.AxisY, model.AxisZ, 0, 1, 0, rx, ry, rz)
    End If
    If MGHNormalize(rx, ry, rz) AndAlso body IsNot Nothing Then
        Dim probe() As Double = { _
            model.BearingX + model.AxisX * 0.04 + rx * (model.InnerRadius + 0.04), _
            model.BearingY + model.AxisY * 0.04 + ry * (model.InnerRadius + 0.04), _
            model.BearingZ + model.AxisZ * 0.04 + rz * (model.InnerRadius + 0.04)}
        Try
            If body.IsPointInside(probe, False) <> Inventor.ContainmentEnum.kInsideContainment Then
                model.AxisX = faceOut.X
                model.AxisY = faceOut.Y
                model.AxisZ = faceOut.Z
            End If
        Catch
        End Try
    End If
    model.MidX = model.BearingX + model.AxisX * model.Thickness / 2.0
    model.MidY = model.BearingY + model.AxisY * model.Thickness / 2.0
    model.MidZ = model.BearingZ + model.AxisZ * model.Thickness / 2.0
    Dim bearingEdge As Inventor.Edge = Nothing
    Dim bearingGap As Double = 0
    Dim haveEdge As Boolean = False
    Try
        For Each e As Inventor.Edge In face.Edges
            Dim edgeCenter As Inventor.Point = Nothing
            Dim edgeRadius As Double = 0
            If Not MGHCircularEdge(e, edgeCenter, edgeRadius) Then Continue For
            Dim gap As Double = System.Math.Abs(edgeRadius - model.InnerRadius)
            If Not haveEdge OrElse gap < bearingGap Then
                bearingEdge = e
                bearingGap = gap
                haveEdge = True
            End If
        Next
    Catch
    End Try
    If haveEdge Then model.BearingEdge = bearingEdge
End Sub

' 1 = aim the screw axis along the face outward normal. The shank is on the solid side
'     of the clicked face, which is the flat top of a countersunk screw.
' -1 = aim the screw axis into the solid. The shank is outside the clicked face,
'     which is the underside of a pan, hex, or socket head.
' 0 = the shank meets the face plane, so the solid probe decides.
Function MGHScrewAxisSense(bearingX As Double, bearingY As Double, bearingZ As Double, _
    faceOutX As Double, faceOutY As Double, faceOutZ As Double, _
    shankX As Double, shankY As Double, shankZ As Double) As Integer
    Dim signed As Double = (shankX - bearingX) * faceOutX + (shankY - bearingY) * faceOutY + (shankZ - bearingZ) * faceOutZ
    If signed > 0.02 Then Return -1
    If signed < -0.02 Then Return 1
    Return 0
End Function

' A drive recess is a short cylinder smaller than the smallest circle on the clicked face.
' A long cylinder is the shank, including when that face is the large top of a flathead.
Function MGHShankQualifies(radius As Double, innerRadius As Double, length As Double) As Boolean
    If radius < 0.04 OrElse radius > 1.5 Then Return False
    If length < 0.05 Then Return False
    If innerRadius > 0.02 AndAlso radius + 0.000000001 < innerRadius * 0.65 AndAlso length < 0.4 Then Return False
    Return True
End Function

' Midpoint of the longest cylinder that can be the screw shank. Thread faces that
' raise E_FAIL are skipped. A drive recess on the underside is too small to qualify.
Function MGHShankMidpoint(body As Inventor.SurfaceBody, innerRadius As Double, _
    faceOutX As Double, faceOutY As Double, faceOutZ As Double, _
    ByRef shankX As Double, ByRef shankY As Double, ByRef shankZ As Double) As Boolean
    shankX = 0 : shankY = 0 : shankZ = 0
    If body Is Nothing Then Return False
    Dim bestLength As Double = 0
    Dim found As Boolean = False
    Try
        For Each shankFace As Inventor.Face In body.Faces
            Try
                Dim cyl As Inventor.Cylinder = TryCast(shankFace.Geometry, Inventor.Cylinder)
                If cyl Is Nothing OrElse cyl.AxisVector Is Nothing OrElse cyl.BasePoint Is Nothing Then Continue For
                Dim align As Double = System.Math.Abs(cyl.AxisVector.X * faceOutX + cyl.AxisVector.Y * faceOutY + cyl.AxisVector.Z * faceOutZ)
                If align < 0.9 Then Continue For
                Dim lowT As Double = 0
                Dim highT As Double = 0
                Dim haveT As Boolean = False
                For Each ed As Inventor.Edge In shankFace.Edges
                    Try
                        Dim samples As New System.Collections.Generic.List(Of Inventor.Point)()
                        Try
                            If ed.StartVertex IsNot Nothing Then samples.Add(ed.StartVertex.Point)
                        Catch
                        End Try
                        Try
                            If ed.StopVertex IsNot Nothing Then samples.Add(ed.StopVertex.Point)
                        Catch
                        End Try
                        Dim edgeCenter As Inventor.Point = Nothing
                        Dim edgeRadius As Double = 0
                        If MGHCircularEdge(ed, edgeCenter, edgeRadius) Then samples.Add(edgeCenter)
                        For Each sample As Inventor.Point In samples
                            Dim along As Double = (sample.X - cyl.BasePoint.X) * cyl.AxisVector.X + (sample.Y - cyl.BasePoint.Y) * cyl.AxisVector.Y + (sample.Z - cyl.BasePoint.Z) * cyl.AxisVector.Z
                            If Not haveT Then
                                lowT = along : highT = along : haveT = True
                            ElseIf along < lowT Then
                                lowT = along
                            ElseIf along > highT Then
                                highT = along
                            End If
                        Next
                    Catch
                    End Try
                Next
                If Not haveT Then Continue For
                Dim length As Double = highT - lowT
                If Not MGHShankQualifies(cyl.Radius, innerRadius, length) Then Continue For
                If found AndAlso length <= bestLength + 0.001 Then Continue For
                Dim midT As Double = (lowT + highT) / 2.0
                shankX = cyl.BasePoint.X + cyl.AxisVector.X * midT
                shankY = cyl.BasePoint.Y + cyl.AxisVector.Y * midT
                shankZ = cyl.BasePoint.Z + cyl.AxisVector.Z * midT
                bestLength = length
                found = True
            Catch
            End Try
        Next
    Catch
        Return False
    End Try
    Return found
End Function

' The clicked face is the underside of a pan or hex head, or the flat top of a flathead.
' The axis points away from the shank, so the tip goes into the hole.
Sub MGHSetScrewBearingFromFace(model As MGHWasherModel, face As Inventor.Face, app As Inventor.Application)
    If model Is Nothing OrElse face Is Nothing Then Throw New System.Exception("the mounting face is missing")
    Dim pl As Inventor.Plane = Nothing
    Try
        pl = TryCast(face.Geometry, Inventor.Plane)
    Catch
        pl = Nothing
    End Try
    If pl Is Nothing Then Throw New System.Exception("Click the flat underside of the screw head, or the flat top of a flathead.")
    Dim bestCenter As Inventor.Point = Nothing
    Dim bestRadius As Double = 0
    Dim bestEdge As Inventor.Edge = Nothing
    Dim haveCircle As Boolean = False
    Try
        For Each e As Inventor.Edge In face.Edges
            Dim edgeCenter As Inventor.Point = Nothing
            Dim edgeRadius As Double = 0
            If Not MGHCircularEdge(e, edgeCenter, edgeRadius) Then Continue For
            If Not haveCircle OrElse edgeRadius < bestRadius Then
                bestCenter = edgeCenter
                bestRadius = edgeRadius
                bestEdge = e
                haveCircle = True
            End If
        Next
    Catch
    End Try
    If haveCircle Then
        model.BearingX = bestCenter.X
        model.BearingY = bestCenter.Y
        model.BearingZ = bestCenter.Z
        model.InnerRadius = bestRadius
        model.BearingEdge = bestEdge
    Else
        Dim sample As Inventor.Point = face.PointOnFace
        model.BearingX = sample.X
        model.BearingY = sample.Y
        model.BearingZ = sample.Z
        If model.InnerRadius <= 0 Then model.InnerRadius = 0.1
    End If
    Dim body As Inventor.SurfaceBody = face.SurfaceBody
    Dim faceOut As Inventor.UnitVector = MGHFaceOutward(face, body, app)
    model.AxisX = -faceOut.X
    model.AxisY = -faceOut.Y
    model.AxisZ = -faceOut.Z
    Dim rx As Double, ry As Double, rz As Double
    If System.Math.Abs(model.AxisX) < 0.9 Then
        MGHCross(model.AxisX, model.AxisY, model.AxisZ, 1, 0, 0, rx, ry, rz)
    Else
        MGHCross(model.AxisX, model.AxisY, model.AxisZ, 0, 1, 0, rx, ry, rz)
    End If
    If MGHNormalize(rx, ry, rz) AndAlso body IsNot Nothing Then
        Dim probe() As Double = { _
            model.BearingX + model.AxisX * 0.04 + rx * (model.InnerRadius + 0.04), _
            model.BearingY + model.AxisY * 0.04 + ry * (model.InnerRadius + 0.04), _
            model.BearingZ + model.AxisZ * 0.04 + rz * (model.InnerRadius + 0.04)}
        Try
            If body.IsPointInside(probe, False) <> Inventor.ContainmentEnum.kInsideContainment Then
                model.AxisX = faceOut.X
                model.AxisY = faceOut.Y
                model.AxisZ = faceOut.Z
            End If
        Catch
        End Try
    End If
    ' The probe above is right for a pan-head underside and wrong for a flathead top:
    ' into the solid from the top points at the shank. Override with the shank side.
    Dim shankX As Double = 0
    Dim shankY As Double = 0
    Dim shankZ As Double = 0
    If MGHShankMidpoint(body, model.InnerRadius, faceOut.X, faceOut.Y, faceOut.Z, shankX, shankY, shankZ) Then
        Dim sense As Integer = MGHScrewAxisSense(model.BearingX, model.BearingY, model.BearingZ, _
            faceOut.X, faceOut.Y, faceOut.Z, shankX, shankY, shankZ)
        If sense > 0 Then
            model.AxisX = faceOut.X
            model.AxisY = faceOut.Y
            model.AxisZ = faceOut.Z
        ElseIf sense < 0 Then
            model.AxisX = -faceOut.X
            model.AxisY = -faceOut.Y
            model.AxisZ = -faceOut.Z
        End If
    End If
    Dim headThickness As Double = 0
    Try
        For Each otherFace As Inventor.Face In body.Faces
            Try
                Dim otherPlane As Inventor.Plane = TryCast(otherFace.Geometry, Inventor.Plane)
                If otherPlane Is Nothing Then Continue For
                If System.Math.Abs(otherPlane.Normal.X * model.AxisX + otherPlane.Normal.Y * model.AxisY + otherPlane.Normal.Z * model.AxisZ) < 0.95 Then Continue For
                Dim otherPoint As Inventor.Point = otherFace.PointOnFace
                Dim along As Double = (otherPoint.X - model.BearingX) * model.AxisX + (otherPoint.Y - model.BearingY) * model.AxisY + (otherPoint.Z - model.BearingZ) * model.AxisZ
                If along > 0.02 AndAlso along < 2.0 AndAlso (headThickness = 0 OrElse along < headThickness) Then headThickness = along
            Catch
            End Try
        Next
    Catch
    End Try
    If headThickness < 0.02 Then headThickness = 0.2
    model.Thickness = headThickness
    model.MidX = model.BearingX + model.AxisX * model.Thickness / 2.0
    model.MidY = model.BearingY + model.AxisY * model.Thickness / 2.0
    model.MidZ = model.BearingZ + model.AxisZ * model.Thickness / 2.0
End Sub

' Asks once, in the assembly, and writes the face reference onto the hardware part.
' hardwareKind is "nut" or "screw".
Function MGHUseMountingFace(app As Inventor.Application, asm As Inventor.AssemblyDocument, _
    model As MGHWasherModel, roleLabel As String, hint As Inventor.Point, _
    notes As System.Collections.Generic.List(Of String), hardwareKind As String) As Boolean
    Dim isScrew As Boolean = String.Equals(hardwareKind, "screw", System.StringComparison.OrdinalIgnoreCase)
    If model Is Nothing OrElse model.Part Is Nothing Then Return False
    Dim saved As Inventor.Face = Nothing
    Try
        saved = MGHLoadMountingFace(model.Part)
    Catch
        saved = Nothing
    End Try
    If saved IsNot Nothing Then
        Try
            If isScrew Then
                MGHSetScrewBearingFromFace(model, saved, app)
            Else
                MGHSetBearingFromFace(model, saved, app)
            End If
            Return True
        Catch
            saved = Nothing
        End Try
    End If
    Dim tg As Inventor.TransientGeometry = app.TransientGeometry
    Dim matrix As Inventor.Matrix = tg.CreateMatrix()
    If hint IsNot Nothing Then matrix.SetTranslation(tg.CreateVector(hint.X, hint.Y, hint.Z), False)
    Dim tempOcc As Inventor.ComponentOccurrence = Nothing
    Try
        tempOcc = asm.ComponentDefinition.Occurrences.AddByComponentDefinition(model.Part.ComponentDefinition, matrix)
        Try
            tempOcc.Grounded = True
        Catch
        End Try
        Try
            tempOcc.Name = MGHUniqueOccurrenceName(asm.ComponentDefinition.Occurrences, If(isScrew, "Click this screw", "Click this nut"))
        Catch
        End Try
        Dim faceTitle As String = If(isScrew, "Which face of the screw head?", "Which nut face touches the washer?")
        Dim faceIntro As String
        Dim facePalette As String
        If isScrew Then
            faceIntro = "A copy of the screw was added at the first hole. It is named """ & tempOcc.Name & """." & vbCrLf & vbCrLf & _
                "For a pan, hex, or socket head, click the flat face under the head. That face sits against the washer." & vbCrLf & _
                "For a flathead screw, click the flat top of the head. The tip is turned into the hole." & vbCrLf & _
                "Do not click the tip of the screw." & vbCrLf & vbCrLf & _
                "That face is saved on the screw file and reused next time." & vbCrLf & _
                "Click OK, then click the face. Cancel on the next window skips this screw."
            facePalette = "Click the underside of the head, or the flat top of a flathead screw. Cancel skips this screw."
        Else
            faceIntro = "A copy of the nut was added at the first hole. It is named """ & tempOcc.Name & """." & vbCrLf & vbCrLf & _
                "Click the flat face that will sit against the washer." & vbCrLf & _
                "On a nylon lock nut, click the smooth metal face. Do not click the nylon ring." & vbCrLf & vbCrLf & _
                "That face is saved on the nut file and reused next time." & vbCrLf & _
                "Click OK, then click the face. Cancel on the next window skips this nut."
            facePalette = "Click the smooth metal face of the added nut. Do not click the nylon ring. Cancel skips this nut."
        End If
        System.Windows.Forms.MessageBox.Show(faceIntro, faceTitle)
        Dim pickedFace As Inventor.Face = Nothing
        Do
            Dim selector As New MGHInteractionSelector()
            Dim gotFace As Boolean = selector.Run(app, Inventor.SelectionFilterEnum.kPartFacePlanarFilter, faceTitle, facePalette, True)
            If Not gotFace OrElse selector.Picked.Count = 0 Then Return False
            Dim proxy As Inventor.FaceProxy = TryCast(selector.Picked(0), Inventor.FaceProxy)
            If proxy Is Nothing OrElse proxy.ContainingOccurrence Is Nothing OrElse _
                Not String.Equals(proxy.ContainingOccurrence.Name, tempOcc.Name, System.StringComparison.OrdinalIgnoreCase) Then
                System.Windows.Forms.MessageBox.Show("Click a flat face on the part named """ & tempOcc.Name & """. That is the part that was just added.", faceTitle)
                Continue Do
            End If
            pickedFace = proxy.NativeObject
            If pickedFace Is Nothing Then
                System.Windows.Forms.MessageBox.Show("That face could not be read from the part.", faceTitle)
                Continue Do
            End If
            Try
                If isScrew Then
                    MGHSetScrewBearingFromFace(model, pickedFace, app)
                Else
                    MGHSetBearingFromFace(model, pickedFace, app)
                End If
                Exit Do
            Catch ex As System.Exception
                System.Windows.Forms.MessageBox.Show(ex.Message, faceTitle)
                pickedFace = Nothing
            End Try
        Loop
        MGHSaveMountingFace(model.Part, pickedFace)
        If model.Part.IsModifiable Then
            model.Part.Save()
            notes.Add(roleLabel & " mounting face saved on " & System.IO.Path.GetFileName(model.FilePath) & ". Delete the MGH Mounting Face iProperties to choose it again.")
        Else
            notes.Add(roleLabel & " mounting face was used, but " & System.IO.Path.GetFileName(model.FilePath) & " is read-only so it was not saved.")
        End If
        Return True
    Finally
        If tempOcc IsNot Nothing Then
            Try
                tempOcc.Delete()
            Catch
                If notes IsNot Nothing Then notes.Add("The temporary " & If(isScrew, "screw", "nut") & " used to choose the mounting face could not be removed.")
            End Try
        End If
    End Try
End Function

Function MGHMatrixMoved(app As Inventor.Application, before As Inventor.Matrix, after As Inventor.Matrix) As Boolean
    Dim tg As Inventor.TransientGeometry = app.TransientGeometry
    Dim samples() As Inventor.Point = { _
        tg.CreatePoint(0, 0, 0), tg.CreatePoint(1, 0, 0), tg.CreatePoint(0, 1, 0), tg.CreatePoint(0, 0, 1)}
    Dim i As Integer
    For i = 0 To samples.Length - 1
        Dim leftPoint As Inventor.Point = samples(i).Copy()
        Dim rightPoint As Inventor.Point = samples(i).Copy()
        leftPoint.TransformBy(before)
        rightPoint.TransformBy(after)
        If leftPoint.DistanceTo(rightPoint) > 0.001 Then Return True
    Next
    Return False
End Function

' Kept for the placement math. Hardware is grounded at the matrix instead of insert-constrained.
Function MGHWasherSitsOutside(occ As Inventor.ComponentOccurrence, model As MGHWasherModel, _
    contact As Inventor.Point, outward As Inventor.UnitVector, app As Inventor.Application) As Boolean
    Dim mid As Inventor.Point = app.TransientGeometry.CreatePoint(model.MidX, model.MidY, model.MidZ)
    mid.TransformBy(occ.Transformation)
    Dim signed As Double = (mid.X - contact.X) * outward.X + (mid.Y - contact.Y) * outward.Y + (mid.Z - contact.Z) * outward.Z
    Return signed > model.Thickness * 0.2
End Function

Function MGHWasherMatrix(app As Inventor.Application, model As MGHWasherModel, _
    contact As Inventor.Point, outward As Inventor.UnitVector) As Inventor.Matrix
    Dim fxx As Double, fxy As Double, fxz As Double, fyx As Double, fyy As Double, fyz As Double
    Dim txx As Double, txy As Double, txz As Double, tyx As Double, tyy As Double, tyz As Double
    MGHWasherBasis(model.AxisX, model.AxisY, model.AxisZ, fxx, fxy, fxz, fyx, fyy, fyz)
    MGHWasherBasis(outward.X, outward.Y, outward.Z, txx, txy, txz, tyx, tyy, tyz)
    Dim tg As Inventor.TransientGeometry = app.TransientGeometry
    Dim matrix As Inventor.Matrix = tg.CreateMatrix()
    matrix.SetToAlignCoordinateSystems( _
        tg.CreatePoint(model.BearingX, model.BearingY, model.BearingZ), _
        tg.CreateVector(fxx, fxy, fxz), tg.CreateVector(fyx, fyy, fyz), _
        tg.CreateVector(model.AxisX, model.AxisY, model.AxisZ), _
        contact, _
        tg.CreateVector(txx, txy, txz), tg.CreateVector(tyx, tyy, tyz), _
        tg.CreateVector(outward.X, outward.Y, outward.Z))
    Return matrix
End Function

' The washer file is already open from the geometry read. Adding it by that
' definition avoids a second open, which raises E_FAIL inside an iLogic rule.
Function MGHAddWasherOccurrence(asm As Inventor.AssemblyDocument, model As MGHWasherModel, _
    matrix As Inventor.Matrix) As Inventor.ComponentOccurrence
    Dim added As Inventor.ComponentOccurrence = Nothing
    If model.Part IsNot Nothing Then
        Try
            added = asm.ComponentDefinition.Occurrences.AddByComponentDefinition(model.Part.ComponentDefinition, matrix)
        Catch
            added = Nothing
        End Try
    End If
    If added IsNot Nothing Then Return added
    Dim filePath As String = model.FilePath
    If (filePath Is Nothing OrElse filePath = "") AndAlso model.Part IsNot Nothing Then filePath = model.Part.FullFileName
    If filePath Is Nothing OrElse filePath = "" Then Throw New System.Exception("the part file path is missing")
    Try
        Return asm.ComponentDefinition.Occurrences.Add(filePath, matrix)
    Catch firstAdd As System.Exception
        ' Close only a hidden part this rule opened. A washer the user already
        ' has on screen keeps its window and any unsaved edits.
        Dim hidden As Boolean = False
        If model.Part IsNot Nothing Then
            Try
                hidden = model.Part.Views.Count = 0
            Catch
                hidden = False
            End Try
        End If
        If hidden Then
            Try
                model.Part.Close(True)
            Catch
            End Try
            model.Part = Nothing
            model.BearingEdge = Nothing
        End If
        Try
            Return asm.ComponentDefinition.Occurrences.Add(filePath, matrix)
        Catch
            Throw New System.Exception("while adding the part to the assembly (" & firstAdd.Message & ")")
        End Try
    End Try
End Function

Function MGHParseStoredPoint(app As Inventor.Application, text As String) As Inventor.Point
    If text Is Nothing OrElse text = "" Then Return Nothing
    Dim parts() As String = text.Split(","c)
    If parts.Length <> 3 Then Return Nothing
    Dim x As Double, y As Double, z As Double
    If Not Double.TryParse(parts(0), System.Globalization.NumberStyles.Float, System.Globalization.CultureInfo.InvariantCulture, x) Then Return Nothing
    If Not Double.TryParse(parts(1), System.Globalization.NumberStyles.Float, System.Globalization.CultureInfo.InvariantCulture, y) Then Return Nothing
    If Not Double.TryParse(parts(2), System.Globalization.NumberStyles.Float, System.Globalization.CultureInfo.InvariantCulture, z) Then Return Nothing
    Return app.TransientGeometry.CreatePoint(x, y, z)
End Function

Function MGHFormatPoint(point As Inventor.Point) As String
    Dim culture As System.Globalization.CultureInfo = System.Globalization.CultureInfo.InvariantCulture
    Return point.X.ToString("0.000000", culture) & "," & point.Y.ToString("0.000000", culture) & "," & point.Z.ToString("0.000000", culture)
End Function

' Nut side is the end the user chose. The washer under the screw uses the other end.
Function MGHWasherUsesSelectedRim(underNut As Boolean, nutOnSelectedRim As Boolean) As Boolean
    If underNut Then Return nutOnSelectedRim
    Return Not nutOnSelectedRim
End Function

' A name from an older run has no end word and matches either end.
' "rim" and "selected" are the clicked hole. "plate" and "opposite" are the plate face.
Function MGHWasherNameMatchesEnd(name As String, endName As String) As Boolean
    If name Is Nothing OrElse name = "" Then Return False
    Dim lower As String = name.ToLowerInvariant()
    Dim hasSelected As Boolean = lower.Contains("selected") OrElse lower.Contains("rim")
    Dim hasOpposite As Boolean = lower.Contains("opposite") OrElse lower.Contains("plate")
    If Not hasSelected AndAlso Not hasOpposite Then Return True
    If String.Equals(endName, "Selected", System.StringComparison.OrdinalIgnoreCase) Then Return hasSelected AndAlso Not hasOpposite
    If String.Equals(endName, "Opposite", System.StringComparison.OrdinalIgnoreCase) Then Return hasOpposite AndAlso Not hasSelected
    Return False
End Function

Sub MGHOffsetPoint(x As Double, y As Double, z As Double, ux As Double, uy As Double, uz As Double, _
    distance As Double, ByRef ox As Double, ByRef oy As Double, ByRef oz As Double)
    ox = x + ux * distance
    oy = y + uy * distance
    oz = z + uz * distance
End Sub

' Older placements were renamed "MGH Nut #6 plate [x,y,z]". New placements keep the part file name.
' The old name is still recognized so a later run can replace those parts.
Function MGHCenterTextFromWasherName(name As String) As String
    If name Is Nothing OrElse name = "" Then Return ""
    Dim washerName As Boolean = name.StartsWith("MGH Washer ", System.StringComparison.OrdinalIgnoreCase)
    Dim nutName As Boolean = name.StartsWith("MGH Nut ", System.StringComparison.OrdinalIgnoreCase)
    Dim screwName As Boolean = name.StartsWith("MGH Screw ", System.StringComparison.OrdinalIgnoreCase)
    If Not washerName AndAlso Not nutName AndAlso Not screwName Then Return ""
    Dim openAt As Integer = name.LastIndexOf("["c)
    Dim closeAt As Integer = name.LastIndexOf("]"c)
    If openAt < 0 OrElse closeAt <= openAt Then Return ""
    Return name.Substring(openAt + 1, closeAt - openAt - 1).Trim()
End Function

Function MGHUniqueOccurrenceName(occs As Inventor.ComponentOccurrences, requested As String) As String
    Dim n As Integer
    For n = 1 To 1000
        Dim candidate As String = If(n = 1, requested, requested & " (" & n.ToString() & ")")
        Dim exists As Boolean = False
        For Each occ As Inventor.ComponentOccurrence In occs
            If String.Equals(occ.Name, candidate, System.StringComparison.OrdinalIgnoreCase) Then
                exists = True
                Exit For
            End If
        Next
        If Not exists Then Return candidate
    Next
    Throw New System.Exception("Could not find an unused component name.")
End Function

Function MGHHardwareNameMatchesRole(name As String, roleName As String) As Boolean
    If name Is Nothing OrElse name = "" Then Return False
    If String.Equals(roleName, "Nut", System.StringComparison.Ordinal) Then
        Return name.StartsWith("MGH Nut ", System.StringComparison.OrdinalIgnoreCase)
    End If
    If String.Equals(roleName, "Screw", System.StringComparison.Ordinal) Then
        Return name.StartsWith("MGH Screw ", System.StringComparison.OrdinalIgnoreCase)
    End If
    Return name.StartsWith("MGH Washer ", System.StringComparison.OrdinalIgnoreCase)
End Function

' Read every existing fastener once. Placement then matches against this list.
Function MGHListExistingHardware(app As Inventor.Application, asm As Inventor.AssemblyDocument) As System.Collections.Generic.List(Of MGHKnownHardware)
    Dim found As New System.Collections.Generic.List(Of MGHKnownHardware)()
    If asm Is Nothing Then Return found
    For Each occ As Inventor.ComponentOccurrence In asm.ComponentDefinition.Occurrences
        Try
            Dim item As MGHKnownHardware = MGHReadKnownHardware(app, occ)
            If item IsNot Nothing Then found.Add(item)
        Catch
        End Try
    Next
    Return found
End Function

Function MGHReadKnownHardware(app As Inventor.Application, occ As Inventor.ComponentOccurrence) As MGHKnownHardware
    If occ Is Nothing Then Return Nothing
    Dim occName As String = ""
    Try
        occName = occ.Name
    Catch
        occName = ""
    End Try
    Dim role As String = ""
    Dim side As String = ""
    Dim hasSide As Boolean = False
    Dim stored As Inventor.Point = Nothing
    Dim fromAttribute As Boolean = False
    Try
        If occ.AttributeSets.NameIsUsed("MGH_Hardware") Then
            fromAttribute = True
            Dim aset As Inventor.AttributeSet = occ.AttributeSets.Item("MGH_Hardware")
            role = MGHGetAttr(aset, "Role")
            stored = MGHParseStoredPoint(app, MGHGetAttr(aset, "Center"))
            side = MGHGetAttr(aset, "Side")
            hasSide = side <> ""
        End If
    Catch
        fromAttribute = False
        stored = Nothing
    End Try
    If Not fromAttribute Then
        If MGHHardwareNameMatchesRole(occName, "Nut") Then
            role = "Nut"
        ElseIf MGHHardwareNameMatchesRole(occName, "Screw") Then
            role = "Screw"
        ElseIf MGHHardwareNameMatchesRole(occName, "Washer") Then
            role = "Washer"
        Else
            Return Nothing
        End If
        stored = MGHParseStoredPoint(app, MGHCenterTextFromWasherName(occName))
    End If
    If stored Is Nothing Then Return Nothing
    Dim item As New MGHKnownHardware()
    item.Occurrence = occ
    item.Role = role
    item.Side = side
    item.HasSide = hasSide
    item.Center = stored
    item.FromAttribute = fromAttribute
    item.Name = occName
    Return item
End Function

Function MGHRemoveWashersAt(known As System.Collections.Generic.List(Of MGHKnownHardware), _
    centers As System.Collections.Generic.List(Of Inventor.Point), keep As Inventor.ComponentOccurrence, _
    endName As String, roleName As String) As Integer
    If known Is Nothing OrElse centers Is Nothing Then Return 0
    Dim removed As Integer = 0
    Dim index As Integer = known.Count - 1
    Do While index >= 0
        Dim item As MGHKnownHardware = known(index)
        Dim drop As Boolean = False
        If item IsNot Nothing AndAlso item.Occurrence IsNot Nothing AndAlso item.Center IsNot Nothing Then
            If keep Is Nothing OrElse Not (item.Occurrence Is keep) Then
                Dim roleOk As Boolean = False
                Dim sideOk As Boolean = True
                If item.FromAttribute Then
                    roleOk = String.Equals(item.Role, roleName, System.StringComparison.Ordinal)
                    If item.HasSide Then sideOk = String.Equals(item.Side, endName, System.StringComparison.OrdinalIgnoreCase)
                Else
                    roleOk = MGHHardwareNameMatchesRole(item.Name, roleName) AndAlso MGHWasherNameMatchesEnd(item.Name, endName)
                End If
                If roleOk AndAlso sideOk Then
                    For Each center As Inventor.Point In centers
                        If item.Center.DistanceTo(center) < 0.005 Then
                            drop = True
                            Exit For
                        End If
                    Next
                End If
            End If
        End If
        If drop Then
            item.Occurrence.Delete()
            known.RemoveAt(index)
            removed += 1
        End If
        index -= 1
    Loop
    Return removed
End Function

Function MGHNativeSelectedEdge(rim As MGHComponentRim) As Inventor.Edge
    If rim Is Nothing OrElse rim.SelectedEdge Is Nothing Then Return Nothing
    Dim proxy As Inventor.EdgeProxy = TryCast(rim.SelectedEdge, Inventor.EdgeProxy)
    If proxy IsNot Nothing Then Return proxy.NativeObject
    Return rim.SelectedEdge
End Function

Function MGHReadEdgeCircle(edge As Inventor.Edge, ByRef cx As Double, ByRef cy As Double, ByRef cz As Double, _
    ByRef radius As Double, ByRef ax As Double, ByRef ay As Double, ByRef az As Double) As Boolean
    cx = 0 : cy = 0 : cz = 0 : radius = 0 : ax = 0 : ay = 0 : az = 0
    If edge Is Nothing Then Return False
    Try
        Dim circ As Inventor.Circle = TryCast(edge.Geometry, Inventor.Circle)
        If circ IsNot Nothing AndAlso circ.Radius > 0 Then
            cx = circ.Center.X : cy = circ.Center.Y : cz = circ.Center.Z
            radius = circ.Radius
            ax = circ.Normal.X : ay = circ.Normal.Y : az = circ.Normal.Z
            Return MGHNormalize(ax, ay, az)
        End If
        Dim arc As Inventor.Arc3d = TryCast(edge.Geometry, Inventor.Arc3d)
        If arc IsNot Nothing AndAlso arc.Radius > 0 Then
            cx = arc.Center.X : cy = arc.Center.Y : cz = arc.Center.Z
            radius = arc.Radius
            ax = arc.Normal.X : ay = arc.Normal.Y : az = arc.Normal.Z
            Return MGHNormalize(ax, ay, az)
        End If
    Catch
    End Try
    Return False
End Function

Function MGHListHasFace(faces As System.Collections.Generic.List(Of Inventor.Face), face As Inventor.Face) As Boolean
    If faces Is Nothing OrElse face Is Nothing Then Return False
    For Each known As Inventor.Face In faces
        If known Is face Then Return True
    Next
    Return False
End Function

Function MGHListHasEdge(edges As System.Collections.Generic.List(Of Inventor.Edge), edge As Inventor.Edge) As Boolean
    If edges Is Nothing OrElse edge Is Nothing Then Return False
    For Each known As Inventor.Edge In edges
        If known Is edge Then Return True
    Next
    Return False
End Function

' Cylinder, cone, or hole fillet sharing the selected hole axis.
Function MGHRoundHoleFace(face As Inventor.Face, cx As Double, cy As Double, cz As Double, _
    radius As Double, ax As Double, ay As Double, az As Double) As Boolean
    If face Is Nothing Then Return False
    Try
        Dim cyl As Inventor.Cylinder = TryCast(face.Geometry, Inventor.Cylinder)
        If cyl IsNot Nothing Then
            If System.Math.Abs(cyl.AxisVector.X * ax + cyl.AxisVector.Y * ay + cyl.AxisVector.Z * az) < 0.95 Then Return False
            If MGHDistanceToAxis(cyl.BasePoint.X, cyl.BasePoint.Y, cyl.BasePoint.Z, cx, cy, cz, ax, ay, az) > System.Math.Max(0.15, radius * 0.5) Then Return False
            If cyl.Radius > radius * 4.0 + 0.05 Then Return False
            Return True
        End If
        Dim cone As Inventor.Cone = TryCast(face.Geometry, Inventor.Cone)
        If cone IsNot Nothing Then
            If System.Math.Abs(cone.AxisVector.X * ax + cone.AxisVector.Y * ay + cone.AxisVector.Z * az) < 0.95 Then Return False
            If MGHDistanceToAxis(cone.BasePoint.X, cone.BasePoint.Y, cone.BasePoint.Z, cx, cy, cz, ax, ay, az) > System.Math.Max(0.2, radius) Then Return False
            Return True
        End If
        Dim tor As Inventor.Torus = TryCast(face.Geometry, Inventor.Torus)
        If tor IsNot Nothing Then
            If System.Math.Abs(tor.AxisVector.X * ax + tor.AxisVector.Y * ay + tor.AxisVector.Z * az) < 0.95 Then Return False
            If MGHDistanceToAxis(tor.CenterPoint.X, tor.CenterPoint.Y, tor.CenterPoint.Z, cx, cy, cz, ax, ay, az) > System.Math.Max(0.2, radius) Then Return False
            If tor.MajorRadius > radius * 4.0 + 0.05 Then Return False
            Return True
        End If
    Catch
    End Try
    Return False
End Function

' Circular rims reached by walking the hole wall, including a chamfer or countersink on the far face.
Function MGHCollectHoleRims(selected As Inventor.Edge, cx As Double, cy As Double, cz As Double, _
    radius As Double, ax As Double, ay As Double, az As Double) As System.Collections.Generic.List(Of Inventor.Edge)
    Dim found As New System.Collections.Generic.List(Of Inventor.Edge)()
    Dim pending As New System.Collections.Generic.List(Of Inventor.Face)()
    Dim seenFaces As New System.Collections.Generic.List(Of Inventor.Face)()
    Dim seenEdges As New System.Collections.Generic.List(Of Inventor.Edge)()
    Try
        For Each startFace As Inventor.Face In selected.Faces
            pending.Add(startFace)
        Next
    Catch
    End Try
    Dim cursor As Integer = 0
    Do While cursor < pending.Count AndAlso seenFaces.Count < 40
        Dim face As Inventor.Face = pending(cursor)
        cursor += 1
        If face Is Nothing OrElse MGHListHasFace(seenFaces, face) Then Continue Do
        seenFaces.Add(face)
        Dim roundFace As Boolean = MGHRoundHoleFace(face, cx, cy, cz, radius, ax, ay, az)
        Dim planeFace As Boolean = False
        Try
            planeFace = TypeOf face.Geometry Is Inventor.Plane
        Catch
            planeFace = False
        End Try
        If Not roundFace AndAlso Not planeFace Then Continue Do
        Try
            For Each ed As Inventor.Edge In face.Edges
                If ed Is Nothing OrElse MGHListHasEdge(seenEdges, ed) Then Continue For
                seenEdges.Add(ed)
                Dim ex As Double, ey As Double, ez As Double, er As Double, eax As Double, eay As Double, eaz As Double
                If MGHReadEdgeCircle(ed, ex, ey, ez, er, eax, eay, eaz) AndAlso MGHChainRadiusOk(er, radius) Then
                    If MGHDistanceToAxis(ex, ey, ez, cx, cy, cz, ax, ay, az) <= System.Math.Max(0.1, radius * 0.35) Then
                        found.Add(ed)
                    End If
                End If
                If roundFace Then
                    Try
                        For Each neighbor As Inventor.Face In ed.Faces
                            If neighbor IsNot Nothing AndAlso Not MGHListHasFace(seenFaces, neighbor) Then pending.Add(neighbor)
                        Next
                    Catch
                    End Try
                End If
            Next
        Catch
        End Try
    Loop
    Return found
End Function

' Far circular rim in the same coordinate space as selected. False when this hole has no other rim.
Function MGHFarRimOfEdge(selected As Inventor.Edge, ByRef farEdge As Inventor.Edge, _
    ByRef farX As Double, ByRef farY As Double, ByRef farZ As Double) As Boolean
    farEdge = Nothing
    farX = 0 : farY = 0 : farZ = 0
    Dim cx As Double, cy As Double, cz As Double, radius As Double, ax As Double, ay As Double, az As Double
    If Not MGHReadEdgeCircle(selected, cx, cy, cz, radius, ax, ay, az) Then Return False
    Dim edges As System.Collections.Generic.List(Of Inventor.Edge) = MGHCollectHoleRims(selected, cx, cy, cz, radius, ax, ay, az)
    Dim candidates As New System.Collections.Generic.List(Of MGHRimCandidate)()
    Dim kept As New System.Collections.Generic.List(Of Inventor.Edge)()
    For Each ed As Inventor.Edge In edges
        Dim ex As Double, ey As Double, ez As Double, er As Double, eax As Double, eay As Double, eaz As Double
        If Not MGHReadEdgeCircle(ed, ex, ey, ez, er, eax, eay, eaz) Then Continue For
        Dim sample As New MGHRimCandidate()
        sample.X = ex : sample.Y = ey : sample.Z = ez : sample.Radius = er
        candidates.Add(sample)
        kept.Add(ed)
    Next
    Dim index As Integer = MGHChooseChainExit(cx, cy, cz, ax, ay, az, radius, candidates)
    If index < 0 Then Return False
    farEdge = kept(index)
    farX = candidates(index).X : farY = candidates(index).Y : farZ = candidates(index).Z
    Return True
End Function

' Exit point of the hole when the far opening is not a circle. Coordinates match the edge.
Function MGHHoleExitPoint(app As Inventor.Application, edge As Inventor.Edge, _
    ByRef farX As Double, ByRef farY As Double, ByRef farZ As Double) As Boolean
    farX = 0 : farY = 0 : farZ = 0
    Dim cx As Double, cy As Double, cz As Double, radius As Double, ax As Double, ay As Double, az As Double
    If Not MGHReadEdgeCircle(edge, cx, cy, cz, radius, ax, ay, az) Then Return False
    Dim body As Inventor.SurfaceBody = Nothing
    Dim planar As Inventor.Face = Nothing
    Try
        For Each f As Inventor.Face In edge.Faces
            If body Is Nothing Then body = f.SurfaceBody
            If planar Is Nothing AndAlso TypeOf f.Geometry Is Inventor.Plane Then planar = f
        Next
    Catch
        Return False
    End Try
    If body Is Nothing OrElse planar Is Nothing Then Return False
    Dim outward As Inventor.UnitVector = Nothing
    Try
        outward = MGHFaceOutward(planar, body, app)
    Catch
        Return False
    End Try
    Dim ix As Double = -outward.X
    Dim iy As Double = -outward.Y
    Dim iz As Double = -outward.Z
    Dim rx As Double, ry As Double, rz As Double
    If System.Math.Abs(ax) < 0.9 Then
        MGHCross(ax, ay, az, 1, 0, 0, rx, ry, rz)
    Else
        MGHCross(ax, ay, az, 0, 1, 0, rx, ry, rz)
    End If
    If Not MGHNormalize(rx, ry, rz) Then Return False
    Dim tg As Inventor.TransientGeometry = app.TransientGeometry
    Dim dir As Inventor.UnitVector = tg.CreateUnitVector(ix, iy, iz)
    Dim radialTry As Integer
    For radialTry = 0 To 1
        Dim radial As Double = If(radialTry = 0, radius + 0.08, radius * 1.8 + 0.08)
        Dim start As Inventor.Point = tg.CreatePoint( _
            cx + rx * radial + outward.X * 0.1, _
            cy + ry * radial + outward.Y * 0.1, _
            cz + rz * radial + outward.Z * 0.1)
        Dim found As Inventor.ObjectsEnumerator = Nothing
        Dim hits As Inventor.ObjectsEnumerator = Nothing
        Try
            body.FindUsingRay(start, dir, 0.02, found, hits, False)
        Catch
            hits = Nothing
        End Try
        If hits Is Nothing OrElse hits.Count < 2 Then Continue For
        Dim firstPt As Inventor.Point = TryCast(hits.Item(1), Inventor.Point)
        Dim secondPt As Inventor.Point = TryCast(hits.Item(2), Inventor.Point)
        If firstPt Is Nothing OrElse secondPt Is Nothing Then Continue For
        Dim d1 As Double = (firstPt.X - start.X) * ix + (firstPt.Y - start.Y) * iy + (firstPt.Z - start.Z) * iz
        Dim d2 As Double = (secondPt.X - start.X) * ix + (secondPt.Y - start.Y) * iy + (secondPt.Z - start.Z) * iz
        Dim thickness As Double = MGHExitThickness(d1, d2)
        If thickness < 0 Then Continue For
        farX = cx + ix * thickness
        farY = cy + iy * thickness
        farZ = cz + iz * thickness
        Return True
    Next
    Return False
End Function

Function MGHNativeEdgeOutward(edge As Inventor.Edge, app As Inventor.Application) As Inventor.UnitVector
    Dim circ As Inventor.Circle = TryCast(edge.Geometry, Inventor.Circle)
    If circ Is Nothing Then Throw New System.Exception("The component hole rim is not circular.")
    Dim normal As Inventor.UnitVector = circ.Normal
    For Each f As Inventor.Face In edge.Faces
        If Not TypeOf f.Geometry Is Inventor.Plane Then Continue For
        Try
            Dim outDir As Inventor.UnitVector = MGHFaceOutward(f, f.SurfaceBody, app)
            If outDir.DotProduct(normal) < 0 Then Return app.TransientGeometry.CreateUnitVector(-normal.X, -normal.Y, -normal.Z)
            Return normal
        Catch
        End Try
    Next
    Return normal
End Function

' Contact and outward are assembly coordinates. The clicked rim's proxy geometry is already
' in assembly space, so the other end is that point plus the part-space hole depth.
' holeEdge is an assembly proxy when one can be made.
' Returns False when the opposite end of this component hole cannot be found.
Function MGHSeatCacheKey(x As Double, y As Double, z As Double, onSelectedRim As Boolean) As String
    Dim culture As System.Globalization.CultureInfo = System.Globalization.CultureInfo.InvariantCulture
    Return x.ToString("0.000000", culture) & "," & y.ToString("0.000000", culture) & "," & z.ToString("0.000000", culture) & If(onSelectedRim, "|S", "|O")
End Function

Sub MGHRememberSeat(cache As System.Collections.Generic.Dictionary(Of String, MGHSeatCacheEntry), cacheKey As String, _
    ok As Boolean, contact As Inventor.Point, outward As Inventor.UnitVector, holeEdge As Inventor.Edge)
    If cache Is Nothing OrElse cacheKey = "" OrElse cache.ContainsKey(cacheKey) Then Return
    Dim entry As New MGHSeatCacheEntry()
    entry.Ok = ok
    entry.Contact = contact
    entry.Outward = outward
    entry.HoleEdge = holeEdge
    cache.Add(cacheKey, entry)
End Sub

Function MGHComponentWasherSeat(app As Inventor.Application, rim As MGHComponentRim, onSelectedRim As Boolean, _
    ByRef contact As Inventor.Point, ByRef outward As Inventor.UnitVector, ByRef holeEdge As Inventor.Edge, _
    Optional cache As System.Collections.Generic.Dictionary(Of String, MGHSeatCacheEntry) = Nothing) As Boolean
    contact = Nothing
    outward = Nothing
    holeEdge = Nothing
    Dim cacheKey As String = ""
    If cache IsNot Nothing AndAlso rim IsNot Nothing Then
        cacheKey = MGHSeatCacheKey(rim.CenterX, rim.CenterY, rim.CenterZ, onSelectedRim)
        If cache.ContainsKey(cacheKey) Then
            Dim hit As MGHSeatCacheEntry = cache(cacheKey)
            contact = hit.Contact
            outward = hit.Outward
            holeEdge = hit.HoleEdge
            Return hit.Ok
        End If
    End If
    If rim Is Nothing OrElse rim.Component Is Nothing OrElse rim.SelectedEdge Is Nothing Then
        Throw New System.Exception("the selected component hole is missing")
    End If
    Dim nativeEdge As Inventor.Edge = MGHNativeSelectedEdge(rim)
    If nativeEdge Is Nothing Then Throw New System.Exception("the selected component rim is missing")
    Dim nativeCirc As Inventor.Circle = TryCast(nativeEdge.Geometry, Inventor.Circle)
    If nativeCirc Is Nothing Then Throw New System.Exception("the selected component rim is not a full circle")
    Dim axisLen As Double = System.Math.Sqrt(rim.AxisX * rim.AxisX + rim.AxisY * rim.AxisY + rim.AxisZ * rim.AxisZ)
    If axisLen < 0.000000001 Then Throw New System.Exception("the selected component rim has no axis")
    Dim axisX As Double = rim.AxisX / axisLen
    Dim axisY As Double = rim.AxisY / axisLen
    Dim axisZ As Double = rim.AxisZ / axisLen
    Dim tg As Inventor.TransientGeometry = app.TransientGeometry
    Dim selectedAsm As Inventor.Point = tg.CreatePoint(rim.CenterX, rim.CenterY, rim.CenterZ)
    Dim farAsm As Inventor.Point = Nothing
    Dim farEdge As Inventor.Edge = Nothing
    ' The clicked rim is already an assembly proxy, so walk that hole in assembly space.
    ' A chamfer or countersink is accepted. A non-circular exit still yields a point.
    Dim haveFar As Boolean = False
    Dim asmFarX As Double, asmFarY As Double, asmFarZ As Double
    Try
        haveFar = MGHFarRimOfEdge(rim.SelectedEdge, farEdge, asmFarX, asmFarY, asmFarZ)
    Catch
        haveFar = False
    End Try
    If Not haveFar Then
        farEdge = Nothing
        Try
            haveFar = MGHHoleExitPoint(app, rim.SelectedEdge, asmFarX, asmFarY, asmFarZ)
        Catch
            haveFar = False
        End Try
    End If
    If haveFar Then
        Dim placedX As Double, placedY As Double, placedZ As Double
        MGHFarRimPoint(selectedAsm.X, selectedAsm.Y, selectedAsm.Z, _
            asmFarX - selectedAsm.X, asmFarY - selectedAsm.Y, asmFarZ - selectedAsm.Z, _
            placedX, placedY, placedZ)
        farAsm = tg.CreatePoint(placedX, placedY, placedZ)
        If farAsm.DistanceTo(selectedAsm) < 0.02 Then
            farAsm = Nothing
            farEdge = Nothing
        End If
    End If
    Dim dirX As Double = 0
    Dim dirY As Double = 0
    Dim dirZ As Double = 0
    If onSelectedRim Then
        holeEdge = rim.SelectedEdge
        contact = selectedAsm
        If farAsm IsNot Nothing Then
            MGHOutwardFromEnds(selectedAsm.X, selectedAsm.Y, selectedAsm.Z, farAsm.X, farAsm.Y, farAsm.Z, True, dirX, dirY, dirZ)
        Else
            Dim partOut As Inventor.UnitVector = MGHNativeEdgeOutward(nativeEdge, app)
            Dim outSign As Double = If(partOut.DotProduct(nativeCirc.Normal) < 0, -1.0, 1.0)
            dirX = outSign * axisX : dirY = outSign * axisY : dirZ = outSign * axisZ
        End If
    Else
        If farAsm Is Nothing Then
            MGHRememberSeat(cache, cacheKey, False, Nothing, Nothing, Nothing)
            Return False
        End If
        contact = farAsm
        holeEdge = farEdge
        MGHOutwardFromEnds(selectedAsm.X, selectedAsm.Y, selectedAsm.Z, farAsm.X, farAsm.Y, farAsm.Z, False, dirX, dirY, dirZ)
    End If
    If dirX * dirX + dirY * dirY + dirZ * dirZ < 0.000000001 Then Throw New System.Exception("the component hole has no outward direction")
    outward = tg.CreateUnitVector(dirX, dirY, dirZ)
    MGHRememberSeat(cache, cacheKey, True, contact, outward, holeEdge)
    Return True
End Function

Function MGHChooseRoleFile(app As Inventor.Application, library As String, sizeName As String, _
    roleFolder As String, roleLabel As String, notes As System.Collections.Generic.List(Of String)) As String
    Dim roleDir As String = MGHResolveRoleDirectory(library, sizeName, roleFolder)
    Dim expected As String = MGHPreferredRoleDirectory(library, sizeName, roleFolder)
    Dim startDir As String = roleDir
    If startDir = "" Then
        System.Windows.Forms.MessageBox.Show( _
            "No " & roleFolder & " folder was found for " & sizeName & "." & vbCrLf & _
            "Expected: " & expected & vbCrLf & _
            "The file window will open at the hardware folder so you can browse to the part.", _
            "Grouped Mounting Hardware")
        startDir = library
    End If
    Dim picked As String = MGHPickPartFile(app, "Select the " & sizeName & " " & roleLabel & " — " & startDir, startDir)
    If picked = "" Then
        notes.Add(sizeName & " " & roleLabel & " was skipped.")
        Return ""
    End If
    If Not picked.EndsWith(".ipt", System.StringComparison.OrdinalIgnoreCase) OrElse Not System.IO.File.Exists(picked) Then
        notes.Add(sizeName & " " & roleLabel & " was skipped because the selected file is not an Inventor part.")
        Return ""
    End If
    Return picked
End Function

Function MGHPlaceHardwareItem(app As Inventor.Application, asm As Inventor.AssemblyDocument, _
    model As MGHWasherModel, contact As Inventor.Point, outward As Inventor.UnitVector, _
    roleName As String, sizeName As String, center As Inventor.Point, _
    endName As String, station As String, sourceFile As String, roleLabel As String, _
    known As System.Collections.Generic.List(Of MGHKnownHardware), _
    notes As System.Collections.Generic.List(Of String), _
    ByRef replaced As Integer) As Integer
    Dim hardwareOcc As Inventor.ComponentOccurrence = Nothing
    Dim kept As Boolean = False
    Dim action As String = "building the position"
    Try
        app.StatusBarText = "Placing " & sizeName & " " & roleLabel
        Dim matrix As Inventor.Matrix = MGHWasherMatrix(app, model, contact, outward)
        action = "adding the " & roleLabel & " to the assembly"
        hardwareOcc = MGHAddWasherOccurrence(asm, model, matrix)
        kept = True
        ' The matrix already puts the bearing face on the contact point. An insert
        ' constraint solves the whole assembly, which took about ten seconds per nut.
        Try
            hardwareOcc.Grounded = True
        Catch
        End Try
        Dim centerText As String = MGHFormatPoint(center)
        Try
            Dim aset As Inventor.AttributeSet = MGHEnsureAttributeSet(hardwareOcc.AttributeSets, "MGH_Hardware")
            MGHPutAttr(aset, "Role", roleName)
            MGHPutAttr(aset, "Size", sizeName)
            MGHPutAttr(aset, "Center", centerText)
            MGHPutAttr(aset, "Side", endName)
            MGHPutAttr(aset, "Station", station)
            MGHPutAttr(aset, "Source", System.IO.Path.GetFileName(sourceFile))
        Catch
            notes.Add(sizeName & " " & roleLabel & " at " & centerText & " is placed, but its identity could not be stored on the assembly.")
        End Try
        Dim oneCenter As New System.Collections.Generic.List(Of Inventor.Point)()
        oneCenter.Add(center)
        Try
            replaced += MGHRemoveWashersAt(known, oneCenter, hardwareOcc, endName, roleName)
        Catch
            notes.Add("The previous " & roleLabel & " at " & centerText & " could not be removed.")
        End Try
        Return 1
    Catch ex As System.Exception
        If hardwareOcc IsNot Nothing AndAlso Not kept Then
            Try
                hardwareOcc.Delete()
            Catch
            End Try
        End If
        notes.Add(sizeName & " " & roleLabel & " at " & MGHFormatPoint(center) & " failed while " & action & ": " & ex.Message)
        Return 0
    End Try
End Function

Function MGHReadScrew(app As Inventor.Application, path As String) As MGHWasherModel
    Dim opened As Inventor.Document = app.Documents.Open(path, False)
    Dim part As Inventor.PartDocument = TryCast(opened, Inventor.PartDocument)
    If part Is Nothing Then Throw New System.Exception("The selected file is not an Inventor part: " & path)
    Dim body As Inventor.SurfaceBody = Nothing
    Dim bestVolume As Double = -1
    For Each candidate As Inventor.SurfaceBody In part.ComponentDefinition.SurfaceBodies
        If Not candidate.IsSolid Then Continue For
        Dim volume As Double = 0
        Try
            volume = candidate.Volume(1.0)
        Catch
            volume = 0
        End Try
        If body Is Nothing OrElse volume > bestVolume Then
            body = candidate
            bestVolume = volume
        End If
    Next
    If body Is Nothing Then Throw New System.Exception("The screw part has no solid body: " & System.IO.Path.GetFileName(path))

    ' Thread faces often raise E_FAIL when their geometry is read. Skip those faces.
    ' The mounting-face prompt replaces this estimate, so a partial read is enough to continue.
    Dim model As New MGHWasherModel()
    model.Part = part
    model.FilePath = path
    model.InnerRadius = 0.1
    model.Thickness = 0.2
    model.AxisX = 0
    model.AxisY = 0
    model.AxisZ = 1
    Dim axisPoint As Inventor.Point = Nothing
    Dim axisDir As Inventor.UnitVector = Nothing
    Dim shankRadius As Double = 0
    Dim shankLow As Double = 0
    Dim shankHigh As Double = 0
    Dim haveShank As Boolean = False
    Try
        For Each f As Inventor.Face In body.Faces
            Try
                Dim cyl As Inventor.Cylinder = TryCast(f.Geometry, Inventor.Cylinder)
                If cyl Is Nothing Then Continue For
                If cyl.Radius < 0.04 OrElse cyl.Radius > 1.5 Then Continue For
                Dim lowT As Double = 0
                Dim highT As Double = 0
                Dim haveT As Boolean = False
                For Each ed As Inventor.Edge In f.Edges
                    Try
                        Dim samples As New System.Collections.Generic.List(Of Inventor.Point)()
                        Try
                            If ed.StartVertex IsNot Nothing Then samples.Add(ed.StartVertex.Point)
                        Catch
                        End Try
                        Try
                            If ed.StopVertex IsNot Nothing Then samples.Add(ed.StopVertex.Point)
                        Catch
                        End Try
                        Dim edgeCenter As Inventor.Point = Nothing
                        Dim edgeRadius As Double = 0
                        If MGHCircularEdge(ed, edgeCenter, edgeRadius) Then samples.Add(edgeCenter)
                        For Each sample As Inventor.Point In samples
                            Dim t As Double = (sample.X - cyl.BasePoint.X) * cyl.AxisVector.X + (sample.Y - cyl.BasePoint.Y) * cyl.AxisVector.Y + (sample.Z - cyl.BasePoint.Z) * cyl.AxisVector.Z
                            If Not haveT Then
                                lowT = t : highT = t : haveT = True
                            ElseIf t < lowT Then
                                lowT = t
                            ElseIf t > highT Then
                                highT = t
                            End If
                        Next
                    Catch
                    End Try
                Next
                If Not haveT Then Continue For
                Dim length As Double = highT - lowT
                If Not haveShank OrElse length > (shankHigh - shankLow) + 0.001 OrElse _
                    (System.Math.Abs(length - (shankHigh - shankLow)) <= 0.001 AndAlso cyl.Radius < shankRadius) Then
                    haveShank = True
                    axisPoint = cyl.BasePoint
                    axisDir = cyl.AxisVector
                    shankRadius = cyl.Radius
                    shankLow = lowT
                    shankHigh = highT
                End If
            Catch
            End Try
        Next
    Catch
        haveShank = False
    End Try
    If haveShank AndAlso axisPoint IsNot Nothing AndAlso axisDir IsNot Nothing Then
        model.InnerRadius = shankRadius
        model.BearingX = axisPoint.X + axisDir.X * shankHigh
        model.BearingY = axisPoint.Y + axisDir.Y * shankHigh
        model.BearingZ = axisPoint.Z + axisDir.Z * shankHigh
        model.AxisX = axisDir.X
        model.AxisY = axisDir.Y
        model.AxisZ = axisDir.Z
        Dim span As Double = System.Math.Abs(shankHigh - shankLow)
        If span > 0.02 Then model.Thickness = System.Math.Min(span, 0.5)
    End If
    model.MidX = model.BearingX + model.AxisX * model.Thickness / 2.0
    model.MidY = model.BearingY + model.AxisY * model.Thickness / 2.0
    model.MidZ = model.BearingZ + model.AxisZ * model.Thickness / 2.0
    Return model
End Function

' Maps a point through an Inventor matrix. Cells are row-major from Matrix.GetMatrixData.
' Translation lives in cells 12, 13, and 14. Apply the left matrix before the right one.
Sub MGHTransformPoint(m() As Double, x As Double, y As Double, z As Double, _
    ByRef outX As Double, ByRef outY As Double, ByRef outZ As Double)
    outX = x * m(0) + y * m(4) + z * m(8) + m(12)
    outY = x * m(1) + y * m(5) + z * m(9) + m(13)
    outZ = x * m(2) + y * m(6) + z * m(10) + m(14)
End Sub

Function MGHMultiplyMatrices(left() As Double, right() As Double) As Double()
    If left Is Nothing OrElse right Is Nothing Then Return Nothing
    If left.Length <> 16 OrElse right.Length <> 16 Then Return Nothing
    Dim product(15) As Double
    Dim row As Integer
    For row = 0 To 3
        Dim col As Integer
        For col = 0 To 3
            Dim sum As Double = 0
            Dim k As Integer
            For k = 0 To 3
                sum += left(row * 4 + k) * right(k * 4 + col)
            Next
            product(row * 4 + col) = sum
        Next
    Next
    Return product
End Function

' locals(0) is the part inside its immediate parent. Each later matrix is the next parent.
Function MGHComposeLeafChain(locals()() As Double) As Double()
    If locals Is Nothing OrElse locals.Length = 0 Then Return Nothing
    Dim total() As Double = CType(locals(0).Clone(), Double())
    Dim i As Integer
    For i = 1 To locals.Length - 1
        total = MGHMultiplyMatrices(total, locals(i))
        If total Is Nothing Then Return Nothing
    Next
    Return total
End Function

' True when every part-space point lands on its assembly-space point and the face normal stays parallel.
Function MGHMatrixMapsPlacement(m() As Double, fromX() As Double, fromY() As Double, fromZ() As Double, _
    toX() As Double, toY() As Double, toZ() As Double, _
    partNx As Double, partNy As Double, partNz As Double, _
    asmNx As Double, asmNy As Double, asmNz As Double) As Boolean
    If m Is Nothing OrElse m.Length <> 16 Then Return False
    If fromX Is Nothing OrElse toX Is Nothing OrElse fromY Is Nothing OrElse toY Is Nothing Then Return False
    If fromZ Is Nothing OrElse toZ Is Nothing Then Return False
    If fromX.Length < 2 OrElse fromX.Length <> toX.Length Then Return False
    If fromY.Length <> fromX.Length OrElse fromZ.Length <> fromX.Length Then Return False
    If toY.Length <> fromX.Length OrElse toZ.Length <> fromX.Length Then Return False
    Dim i As Integer
    For i = 0 To fromX.Length - 1
        Dim x As Double, y As Double, z As Double
        MGHTransformPoint(m, fromX(i), fromY(i), fromZ(i), x, y, z)
        Dim dx As Double = x - toX(i)
        Dim dy As Double = y - toY(i)
        Dim dz As Double = z - toZ(i)
        If dx * dx + dy * dy + dz * dz > 0.000025 Then Return False ' 0.005 cm
    Next
    Dim tipX As Double, tipY As Double, tipZ As Double
    Dim baseX As Double, baseY As Double, baseZ As Double
    MGHTransformPoint(m, fromX(0) + partNx, fromY(0) + partNy, fromZ(0) + partNz, tipX, tipY, tipZ)
    MGHTransformPoint(m, fromX(0), fromY(0), fromZ(0), baseX, baseY, baseZ)
    Dim vx As Double = tipX - baseX
    Dim vy As Double = tipY - baseY
    Dim vz As Double = tipZ - baseZ
    Dim vLen As Double = System.Math.Sqrt(vx * vx + vy * vy + vz * vz)
    Dim aLen As Double = System.Math.Sqrt(asmNx * asmNx + asmNy * asmNy + asmNz * asmNz)
    If vLen < 0.000000001 OrElse aLen < 0.000000001 Then Return False
    Dim dot As Double = (vx * asmNx + vy * asmNy + vz * asmNz) / (vLen * aLen)
    Return System.Math.Abs(dot) > 0.999
End Function

' 0 keeps the occurrence transform. 1 uses the multiplied parent chain. -1 rejects both.
' Fewer than two separated points is not evidence, so the occurrence transform is kept.
Function MGHChoosePartToAssembly(direct() As Double, composed() As Double, _
    fromX() As Double, fromY() As Double, fromZ() As Double, _
    toX() As Double, toY() As Double, toZ() As Double, _
    partNx As Double, partNy As Double, partNz As Double, _
    asmNx As Double, asmNy As Double, asmNz As Double) As Integer
    If fromX Is Nothing OrElse fromX.Length < 2 Then Return 0
    If partNx * partNx + partNy * partNy + partNz * partNz < 0.000000001 Then Return 0
    If asmNx * asmNx + asmNy * asmNy + asmNz * asmNz < 0.000000001 Then Return 0
    Dim separated As Boolean = False
    Dim i As Integer
    For i = 1 To fromX.Length - 1
        Dim dx As Double = fromX(i) - fromX(0)
        Dim dy As Double = fromY(i) - fromY(0)
        Dim dz As Double = fromZ(i) - fromZ(0)
        If dx * dx + dy * dy + dz * dz > 0.0025 Then separated = True ' 0.05 cm
    Next
    If Not separated Then Return 0
    If MGHMatrixMapsPlacement(direct, fromX, fromY, fromZ, toX, toY, toZ, partNx, partNy, partNz, asmNx, asmNy, asmNz) Then Return 0
    If MGHMatrixMapsPlacement(composed, fromX, fromY, fromZ, toX, toY, toZ, partNx, partNy, partNz, asmNx, asmNy, asmNz) Then Return 1
    Return -1
End Function

Function MGHMatrixCells(matrix As Inventor.Matrix) As Double()
    Dim cells(15) As Double
    matrix.GetMatrixData(cells)
    Return cells
End Function

Function MGHParentOccurrence(occ As Inventor.ComponentOccurrence) As Inventor.ComponentOccurrence
    If occ Is Nothing Then Return Nothing
    Try
        Return occ.ParentOccurrence
    Catch
        Return Nothing
    End Try
End Function

' The transform that places this occurrence in its immediate parent, not in a higher assembly.
Function MGHLocalOccurrenceTransform(occ As Inventor.ComponentOccurrence) As Inventor.Matrix
    If occ Is Nothing Then Return Nothing
    Dim proxy As Inventor.ComponentOccurrenceProxy = TryCast(occ, Inventor.ComponentOccurrenceProxy)
    If proxy IsNot Nothing Then
        Try
            Dim native As Inventor.ComponentOccurrence = TryCast(proxy.NativeObject, Inventor.ComponentOccurrence)
            If native IsNot Nothing Then Return native.Transformation.Copy()
        Catch
        End Try
    End If
    Return occ.Transformation.Copy()
End Function

Function MGHComposeToContext(occ As Inventor.ComponentOccurrence) As Inventor.Matrix
    If occ Is Nothing Then Return Nothing
    Dim total As Inventor.Matrix = MGHLocalOccurrenceTransform(occ)
    If total Is Nothing Then Return Nothing
    Dim cursor As Inventor.ComponentOccurrence = MGHParentOccurrence(occ)
    Dim guard As Integer = 0
    Do While cursor IsNot Nothing AndAlso guard < 32
        Dim local As Inventor.Matrix = MGHLocalOccurrenceTransform(cursor)
        If local Is Nothing Then Return Nothing
        total.PostMultiplyBy(local)
        cursor = MGHParentOccurrence(cursor)
        guard += 1
    Loop
    Return total
End Function

Function MGHReadVertexSamples(nativeFace As Inventor.Face, faceProxy As Inventor.Face, _
    ByRef fromX() As Double, ByRef fromY() As Double, ByRef fromZ() As Double, _
    ByRef toX() As Double, ByRef toY() As Double, ByRef toZ() As Double) As Boolean
    fromX = Nothing : fromY = Nothing : fromZ = Nothing
    toX = Nothing : toY = Nothing : toZ = Nothing
    Dim nCount As Integer = 0
    Dim pCount As Integer = 0
    Try
        nCount = nativeFace.Vertices.Count
        pCount = faceProxy.Vertices.Count
    Catch
        Return False
    End Try
    If nCount < 2 OrElse nCount <> pCount Then Return False
    Dim take As Integer = nCount
    If take > 4 Then take = 4
    Dim fx As New System.Collections.Generic.List(Of Double)()
    Dim fy As New System.Collections.Generic.List(Of Double)()
    Dim fz As New System.Collections.Generic.List(Of Double)()
    Dim tx As New System.Collections.Generic.List(Of Double)()
    Dim ty As New System.Collections.Generic.List(Of Double)()
    Dim tz As New System.Collections.Generic.List(Of Double)()
    Dim i As Integer
    For i = 1 To take
        Try
            Dim np As Inventor.Point = nativeFace.Vertices.Item(i).Point
            Dim pp As Inventor.Point = faceProxy.Vertices.Item(i).Point
            fx.Add(np.X) : fy.Add(np.Y) : fz.Add(np.Z)
            tx.Add(pp.X) : ty.Add(pp.Y) : tz.Add(pp.Z)
        Catch
        End Try
    Next
    If fx.Count < 2 Then Return False
    fromX = fx.ToArray() : fromY = fy.ToArray() : fromZ = fz.ToArray()
    toX = tx.ToArray() : toY = ty.ToArray() : toZ = tz.ToArray()
    Return True
End Function

Sub MGHAppendEdgeSamples(nativeEdge As Inventor.Edge, proxyEdge As Inventor.Edge, _
    fx As System.Collections.Generic.List(Of Double), fy As System.Collections.Generic.List(Of Double), fz As System.Collections.Generic.List(Of Double), _
    tx As System.Collections.Generic.List(Of Double), ty As System.Collections.Generic.List(Of Double), tz As System.Collections.Generic.List(Of Double))
    If nativeEdge Is Nothing OrElse proxyEdge Is Nothing Then Exit Sub
    If fx Is Nothing OrElse fx.Count >= 4 Then Exit Sub
    Try
        Dim nMin As Double, nMax As Double, pMin As Double, pMax As Double
        nativeEdge.Evaluator.GetParamExtents(nMin, nMax)
        proxyEdge.Evaluator.GetParamExtents(pMin, pMax)
        If System.Math.Abs(nMin - pMin) > 0.000001 Then Exit Sub
        If System.Math.Abs(nMax - pMax) > 0.000001 Then Exit Sub
        If System.Math.Abs(nMax - nMin) < 0.000001 Then Exit Sub
        Dim params(1) As Double
        params(0) = nMin
        params(1) = nMin + (nMax - nMin) * 0.37
        Dim nPts(5) As Double
        Dim pPts(5) As Double
        nativeEdge.Evaluator.GetPointAtParam(params, nPts)
        proxyEdge.Evaluator.GetPointAtParam(params, pPts)
        Dim k As Integer
        For k = 0 To 1
            fx.Add(nPts(k * 3))
            fy.Add(nPts(k * 3 + 1))
            fz.Add(nPts(k * 3 + 2))
            tx.Add(pPts(k * 3))
            ty.Add(pPts(k * 3 + 1))
            tz.Add(pPts(k * 3 + 2))
        Next
    Catch
    End Try
End Sub

Function MGHReadEdgeSamples(nativeFace As Inventor.Face, faceProxy As Inventor.Face, _
    ByRef fromX() As Double, ByRef fromY() As Double, ByRef fromZ() As Double, _
    ByRef toX() As Double, ByRef toY() As Double, ByRef toZ() As Double) As Boolean
    fromX = Nothing : fromY = Nothing : fromZ = Nothing
    toX = Nothing : toY = Nothing : toZ = Nothing
    Dim nCount As Integer = 0
    Dim pCount As Integer = 0
    Try
        nCount = nativeFace.Edges.Count
        pCount = faceProxy.Edges.Count
    Catch
        Return False
    End Try
    If nCount < 1 OrElse nCount <> pCount Then Return False
    Dim fx As New System.Collections.Generic.List(Of Double)()
    Dim fy As New System.Collections.Generic.List(Of Double)()
    Dim fz As New System.Collections.Generic.List(Of Double)()
    Dim tx As New System.Collections.Generic.List(Of Double)()
    Dim ty As New System.Collections.Generic.List(Of Double)()
    Dim tz As New System.Collections.Generic.List(Of Double)()
    Dim i As Integer
    For i = 1 To nCount
        If fx.Count >= 4 Then Exit For
        MGHAppendEdgeSamples(nativeFace.Edges.Item(i), faceProxy.Edges.Item(i), fx, fy, fz, tx, ty, tz)
    Next
    If fx.Count < 2 Then Return False
    fromX = fx.ToArray() : fromY = fy.ToArray() : fromZ = fz.ToArray()
    toX = tx.ToArray() : toY = ty.ToArray() : toZ = tz.ToArray()
    Return True
End Function

' Nothing means the face points disagree with every candidate, so the rule must not cut.
' A top-level part uses its own transform. A nested part uses the proxy transform when
' that transform lands the part face on the clicked face, and the parent chain otherwise.
Function MGHPartToAssembly(occ As Inventor.ComponentOccurrence, _
    nativeFace As Inventor.Face, faceProxy As Inventor.Face) As Inventor.Matrix
    If occ Is Nothing Then Return Nothing
    Dim direct As Inventor.Matrix = occ.Transformation.Copy()
    If Not TypeOf occ Is Inventor.ComponentOccurrenceProxy Then Return direct
    Dim partNx As Double = 0
    Dim partNy As Double = 0
    Dim partNz As Double = 0
    Dim asmNx As Double = 0
    Dim asmNy As Double = 0
    Dim asmNz As Double = 0
    Try
        Dim partPlane As Inventor.Plane = TryCast(nativeFace.Geometry, Inventor.Plane)
        Dim asmPlane As Inventor.Plane = TryCast(faceProxy.Geometry, Inventor.Plane)
        If partPlane Is Nothing OrElse asmPlane Is Nothing Then Return direct
        partNx = partPlane.Normal.X : partNy = partPlane.Normal.Y : partNz = partPlane.Normal.Z
        asmNx = asmPlane.Normal.X : asmNy = asmPlane.Normal.Y : asmNz = asmPlane.Normal.Z
    Catch
        Return direct
    End Try
    Dim composed As Inventor.Matrix = Nothing
    Dim directCells() As Double = Nothing
    Dim composedCells() As Double = Nothing
    Try
        composed = MGHComposeToContext(occ)
        directCells = MGHMatrixCells(direct)
        If composed IsNot Nothing Then composedCells = MGHMatrixCells(composed)
    Catch
        Return direct
    End Try
    Dim tried As Boolean = False
    Dim fromX() As Double = Nothing
    Dim fromY() As Double = Nothing
    Dim fromZ() As Double = Nothing
    Dim toX() As Double = Nothing
    Dim toY() As Double = Nothing
    Dim toZ() As Double = Nothing
    If MGHReadVertexSamples(nativeFace, faceProxy, fromX, fromY, fromZ, toX, toY, toZ) Then
        tried = True
        Dim vertexChoice As Integer = MGHChoosePartToAssembly(directCells, composedCells, fromX, fromY, fromZ, toX, toY, toZ, partNx, partNy, partNz, asmNx, asmNy, asmNz)
        If vertexChoice = 0 Then Return direct
        If vertexChoice = 1 AndAlso composed IsNot Nothing Then Return composed.Copy()
    End If
    If MGHReadEdgeSamples(nativeFace, faceProxy, fromX, fromY, fromZ, toX, toY, toZ) Then
        tried = True
        Dim edgeChoice As Integer = MGHChoosePartToAssembly(directCells, composedCells, fromX, fromY, fromZ, toX, toY, toZ, partNx, partNy, partNz, asmNx, asmNy, asmNz)
        If edgeChoice = 0 Then Return direct
        If edgeChoice = 1 AndAlso composed IsNot Nothing Then Return composed.Copy()
    End If
    If Not tried Then Return direct
    Return Nothing
End Function

' Native circular edge of the plate hole nearest this plate-space center.
' Placement does not call this. Walking every edge of a heavy plate once per nut
' was one of the costs that made each fastener take several seconds.
Function MGHPlateRimEdge(plateOcc As Inventor.ComponentOccurrence, center As Inventor.Point) As Inventor.Edge
    If plateOcc Is Nothing OrElse center Is Nothing Then Return Nothing
    Dim def As Inventor.PartComponentDefinition = TryCast(plateOcc.Definition, Inventor.PartComponentDefinition)
    If def Is Nothing Then Return Nothing
    Dim best As Inventor.Edge = Nothing
    Dim bestDist As Double = 0
    For Each body As Inventor.SurfaceBody In def.SurfaceBodies
        For Each f As Inventor.Face In body.Faces
            For Each ed As Inventor.Edge In f.Edges
                Dim edgeCenter As Inventor.Point = Nothing
                Dim radius As Double = 0
                If Not MGHCircularEdge(ed, edgeCenter, radius) Then Continue For
                Dim dist As Double = edgeCenter.DistanceTo(center)
                If dist > 0.08 Then Continue For
                If best Is Nothing OrElse dist < bestDist Then
                    best = ed
                    bestDist = dist
                End If
            Next
        Next
    Next
    Return best
End Function

' The plate-face side. contact is on the face the user selected, in assembly space.
Function MGHPlateHardwareSeat(app As Inventor.Application, plateOcc As Inventor.ComponentOccurrence, _
    plateToAssembly As Inventor.Matrix, _
    outX As Double, outY As Double, outZ As Double, center As Inventor.Point, _
    ByRef contact As Inventor.Point, ByRef outward As Inventor.UnitVector, ByRef holeEdge As Inventor.Edge) As Boolean
    contact = Nothing
    outward = Nothing
    holeEdge = Nothing
    If plateOcc Is Nothing OrElse center Is Nothing Then Return False
    Dim length As Double = System.Math.Sqrt(outX * outX + outY * outY + outZ * outZ)
    If length < 0.000000001 Then Return False
    Dim plateMatrix As Inventor.Matrix = plateToAssembly
    If plateMatrix Is Nothing Then plateMatrix = plateOcc.Transformation
    contact = center.Copy()
    contact.TransformBy(plateMatrix)
    outward = app.TransientGeometry.CreateUnitVector(outX / length, outY / length, outZ / length)
    ' The plate contact is this face point. Searching every edge for a rim was only
    ' used by the insert constraint, and that search walked the whole heavy part once per nut.
    holeEdge = Nothing
    Return True
End Function

' Distance from one clicked rim to the plate face, in centimeters. -1 when the rim was not recorded.
Function MGHHoleGripCm(app As Inventor.Application, plateOcc As Inventor.ComponentOccurrence, _
    plateToAssembly As Inventor.Matrix, center As Inventor.Point, rim As MGHComponentRim) As Double
    If app Is Nothing OrElse plateOcc Is Nothing OrElse center Is Nothing OrElse rim Is Nothing Then Return -1
    Dim plateMatrix As Inventor.Matrix = plateToAssembly
    If plateMatrix Is Nothing Then plateMatrix = plateOcc.Transformation
    Dim platePoint As Inventor.Point = center.Copy()
    platePoint.TransformBy(plateMatrix)
    Dim rimPoint As Inventor.Point = app.TransientGeometry.CreatePoint(rim.CenterX, rim.CenterY, rim.CenterZ)
    Return platePoint.DistanceTo(rimPoint)
End Function

Function MGHChooseScrewFile(app As Inventor.Application, library As String, sizeName As String, _
    gripIn As Double, screwWasherIn As Double, nutWasherIn As Double, nutIn As Double, _
    holeCount As Integer, groupText As String, _
    notes As System.Collections.Generic.List(Of String)) As String
    Dim requiredInches As Double = gripIn + screwWasherIn + nutWasherIn + nutIn
    If requiredInches < 0 Then requiredInches = 0
    Dim roleDir As String = MGHResolveRoleDirectory(library, sizeName, "Screws")
    Dim expected As String = MGHPreferredRoleDirectory(library, sizeName, "Screws")
    Dim startDir As String = roleDir
    Dim folderLabel As String = ""
    Dim tooShort As Boolean = False
    If startDir = "" Then
        startDir = library
        notes.Add("No Screws folder was found for " & sizeName & ". Expected: " & expected)
    Else
        Dim folderNames As New System.Collections.Generic.List(Of String)()
        Try
            For Each full As String In System.IO.Directory.GetDirectories(startDir)
                folderNames.Add(System.IO.Path.GetFileName(full))
            Next
        Catch
        End Try
        Dim best As String = MGHBestLengthFolder(folderNames.ToArray(), requiredInches, tooShort)
        If best <> "" Then
            Dim lengthDir As String = System.IO.Path.Combine(startDir, best)
            If System.IO.Directory.Exists(lengthDir) Then
                startDir = lengthDir
                folderLabel = best
            End If
        End If
        If tooShort Then
            notes.Add(sizeName & " needs a screw at least " & MGHFormatInches(requiredInches) & " in, which is longer than the longest " & best & " folder.")
        Else
            notes.Add(sizeName & " screw length needed: " & MGHFormatInches(requiredInches) & " in.")
        End If
    End If
    Dim lengthText As String = MGHScrewLengthMessage(sizeName, gripIn, screwWasherIn, nutWasherIn, nutIn, folderLabel, tooShort, holeCount, groupText)
    Dim lengthTitle As String = MGHFormatInches(requiredInches) & " in — select the " & sizeName & " screw"
    If holeCount > 0 Then lengthTitle &= " (" & holeCount.ToString() & " holes)"
    If System.Windows.Forms.MessageBox.Show(lengthText, lengthTitle, System.Windows.Forms.MessageBoxButtons.OKCancel) <> System.Windows.Forms.DialogResult.OK Then
        notes.Add(sizeName & " " & MGHFormatInches(requiredInches) & " in screw was skipped.")
        Return ""
    End If
    Dim picked As String = MGHPickPartFile(app, lengthTitle, startDir)
    If picked = "" Then
        notes.Add(sizeName & " " & MGHFormatInches(requiredInches) & " in screw was skipped.")
        Return ""
    End If
    If Not picked.EndsWith(".ipt", System.StringComparison.OrdinalIgnoreCase) OrElse Not System.IO.File.Exists(picked) Then
        notes.Add(sizeName & " " & MGHFormatInches(requiredInches) & " in screw was skipped because the selected file is not an Inventor part.")
        Return ""
    End If
    Return picked
End Function

Function MGHPlaceWashers(app As Inventor.Application, asm As Inventor.AssemblyDocument, _
    groups As System.Collections.Generic.SortedDictionary(Of String, OutputGroup), _
    plateOcc As Inventor.ComponentOccurrence, plateToAssembly As Inventor.Matrix, _
    plateOutX As Double, plateOutY As Double, plateOutZ As Double) As String
    Dim notes As New System.Collections.Generic.List(Of String)()
    Dim hardwareProgress As Inventor.ProgressBar = Nothing
    ' iLogic already has a transaction open on the assembly. Starting a second one
    ' raises E_FAIL, so these edits are not wrapped in another assembly transaction.
    Dim stepName As String = "Preparing washer placement"
    Dim deferArmed As Boolean = False
    Dim previousDefer As Boolean = False
    Try
    Dim sizes As New System.Collections.Generic.List(Of String)()
    For Each g As OutputGroup In groups.Values
        Dim folderNames() As String = MGHSizeFolderNames(g.Screw)
        If folderNames.Length = 0 Then
            If g.Screw IsNot Nothing AndAlso String.Equals(g.Screw.Trim(), "Custom", System.StringComparison.OrdinalIgnoreCase) Then
                notes.Add("Custom fastener '" & g.Label & "' has no size folder, so no washer was requested.")
            End If
            Continue For
        End If
        Dim sizeName As String = g.Screw.Trim()
        If Not sizes.Contains(sizeName) Then sizes.Add(sizeName)
    Next
    If sizes.Count = 0 Then
        If notes.Count = 0 Then Return "Washers: no fastener sizes to match a hardware folder."
        Return "Washers were not placed." & vbCrLf & String.Join(vbCrLf, notes.ToArray())
    End If

    Dim library As String = MGHReadHardwareLibrary(asm)
    If library = "" OrElse Not System.IO.Directory.Exists(library) Then library = MGHDefaultHardwareLibrary()
    Dim sideDialog As New MGHWasherSideDialog(library)
    Dim sideResult As System.Windows.Forms.DialogResult = sideDialog.ShowDialog()
    Dim nutOnSelectedRim As Boolean = sideDialog.NutOnSelectedRim
    Dim placeUnderScrew As Boolean = sideDialog.WasherUnderScrew
    Dim placeUnderNut As Boolean = sideDialog.WasherUnderNut
    Dim placeNut As Boolean = sideDialog.PlaceNut
    Dim placeScrew As Boolean = sideDialog.PlaceScrew
    library = sideDialog.LibraryPath
    sideDialog.Dispose()
    If sideResult <> System.Windows.Forms.DialogResult.OK Then Return "Hardware: skipped."
    If library = "" OrElse Not System.IO.Directory.Exists(library) Then
        Dim browsed As String = MGHBrowseHardwareLibrary(library)
        If browsed = "" OrElse Not System.IO.Directory.Exists(browsed) Then Return "Washers: skipped. The hardware folder was not found."
        library = browsed
    End If
    stepName = "Saving the hardware folder"
    If library.Length > 255 Then
        notes.Add("The hardware folder path is longer than 255 characters, so it will not be remembered on the assembly.")
    Else
        Try
            MGHWriteHardwareLibrary(asm, library)
        Catch
            notes.Add("The hardware folder could not be saved on the assembly. Placement will continue.")
        End Try
    End If

    Dim placeWashers As Boolean = placeUnderScrew OrElse placeUnderNut
    stepName = "Choosing a hardware file"
    Dim chosenWashers As New System.Collections.Generic.Dictionary(Of String, String)(System.StringComparer.OrdinalIgnoreCase)
    Dim chosenNuts As New System.Collections.Generic.Dictionary(Of String, String)(System.StringComparer.OrdinalIgnoreCase)
    For Each sizeName As String In sizes
        If placeWashers Then
            Dim washerFile As String = MGHChooseRoleFile(app, library, sizeName, "Washers", "washer", notes)
            If washerFile <> "" Then chosenWashers.Add(sizeName, washerFile)
        End If
        If placeNut Then
            Dim nutFile As String = MGHChooseRoleFile(app, library, sizeName, "Nuts", "nut", notes)
            If nutFile <> "" Then chosenNuts.Add(sizeName, nutFile)
        End If
    Next
    If chosenWashers.Count = 0 AndAlso chosenNuts.Count = 0 AndAlso Not placeScrew Then
        Return "Hardware: no files selected." & If(notes.Count = 0, "", vbCrLf & String.Join(vbCrLf, notes.ToArray()))
    End If

    stepName = "Reading the hardware part"
    Dim washerModels As New System.Collections.Generic.Dictionary(Of String, MGHWasherModel)(System.StringComparer.OrdinalIgnoreCase)
    Dim nutModels As New System.Collections.Generic.Dictionary(Of String, MGHWasherModel)(System.StringComparer.OrdinalIgnoreCase)
    For Each sizeName As String In New System.Collections.Generic.List(Of String)(chosenWashers.Keys)
        Try
            washerModels.Add(sizeName, MGHReadWasher(app, chosenWashers(sizeName)))
        Catch ex As System.Exception
            notes.Add(sizeName & " washer was not placed (" & ex.Message & ").")
            chosenWashers.Remove(sizeName)
        End Try
    Next
    Dim faceHint As Inventor.Point = Nothing
    For Each hinted As OutputGroup In groups.Values
        If hinted.Rims IsNot Nothing AndAlso hinted.Rims.Count > 0 AndAlso hinted.Rims(0) IsNot Nothing Then
            faceHint = app.TransientGeometry.CreatePoint(hinted.Rims(0).CenterX, hinted.Rims(0).CenterY, hinted.Rims(0).CenterZ)
            Exit For
        End If
    Next
    For Each sizeName As String In New System.Collections.Generic.List(Of String)(chosenNuts.Keys)
        Try
            stepName = "Reading the nut"
            Dim nutModel As MGHWasherModel = MGHReadWasher(app, chosenNuts(sizeName))
            stepName = "Choosing the nut mounting face"
            If Not MGHUseMountingFace(app, asm, nutModel, sizeName & " nut", faceHint, notes, "nut") Then
                notes.Add(sizeName & " nut was skipped because its mounting face was not selected.")
                chosenNuts.Remove(sizeName)
            Else
                nutModels.Add(sizeName, nutModel)
            End If
        Catch ex As System.Exception
            notes.Add(sizeName & " nut was not placed (" & ex.Message & ").")
            chosenNuts.Remove(sizeName)
        End Try
    Next
    Dim chosenScrews As New System.Collections.Generic.Dictionary(Of String, String)(System.StringComparer.OrdinalIgnoreCase)
    If placeScrew Then
        stepName = "Choosing a screw"
        Dim screwRequests As New System.Collections.Generic.List(Of MGHScrewRequest)()
        Dim requestsByKey As New System.Collections.Generic.Dictionary(Of String, MGHScrewRequest)(System.StringComparer.OrdinalIgnoreCase)
        For Each g As OutputGroup In groups.Values
            If g.Screw Is Nothing Then Continue For
            If MGHSizeFolderNames(g.Screw).Length = 0 Then Continue For
            Dim sizeName As String = g.Screw.Trim()
            Dim washerCm As Double = 0
            If washerModels.ContainsKey(sizeName) Then washerCm = washerModels(sizeName).Thickness
            Dim nutCm As Double = 0
            If placeNut AndAlso nutModels.ContainsKey(sizeName) Then nutCm = nutModels(sizeName).Thickness
            Dim screwWasherIn As Double = 0
            Dim nutWasherIn As Double = 0
            Dim nutIn As Double = 0
            MGHScrewAllowances(washerCm, nutCm, placeUnderScrew, placeUnderNut, placeNut AndAlso nutCm > 0, screwWasherIn, nutWasherIn, nutIn)
            Dim missingRim As Boolean = False
            Dim centerIndex As Integer
            For centerIndex = 0 To g.Centers.Count - 1
                Dim rim As MGHComponentRim = Nothing
                If g.Rims IsNot Nothing AndAlso centerIndex < g.Rims.Count Then rim = g.Rims(centerIndex)
                Dim gripCm As Double = MGHHoleGripCm(app, plateOcc, plateToAssembly, g.Centers(centerIndex), rim)
                If gripCm < 0 Then
                    gripCm = 0
                    missingRim = True
                End If
                Dim requiredInches As Double = MGHScrewRequiredInches(gripCm, screwWasherIn, nutWasherIn, nutIn)
                Dim lengthKey As String = MGHScrewLengthKey(sizeName, requiredInches)
                Dim request As MGHScrewRequest = Nothing
                If Not requestsByKey.ContainsKey(lengthKey) Then
                    request = New MGHScrewRequest()
                    request.Key = lengthKey
                    request.SizeName = sizeName
                    request.RequiredInches = requiredInches
                    request.GripIn = If(gripCm > 0, gripCm / 2.54, 0)
                    request.ScrewWasherIn = screwWasherIn
                    request.NutWasherIn = nutWasherIn
                    request.NutIn = nutIn
                    request.HoleCount = 1
                    requestsByKey.Add(lengthKey, request)
                    screwRequests.Add(request)
                Else
                    request = requestsByKey(lengthKey)
                    request.HoleCount += 1
                    Dim gripIn As Double = If(gripCm > 0, gripCm / 2.54, 0)
                    If gripIn > request.GripIn Then
                        request.GripIn = gripIn
                        request.RequiredInches = requiredInches
                    End If
                End If
                Dim groupLabel As String = ""
                If g.Label IsNot Nothing Then groupLabel = g.Label.Trim()
                If groupLabel <> "" AndAlso Not request.GroupLabels.Contains(groupLabel) Then request.GroupLabels.Add(groupLabel)
            Next
            If missingRim Then notes.Add(sizeName & " screw length does not include every part, because a hole rim was not recorded.")
        Next
        For Each request As MGHScrewRequest In screwRequests
            Dim screwFile As String = MGHChooseScrewFile(app, library, request.SizeName, request.GripIn, request.ScrewWasherIn, request.NutWasherIn, request.NutIn, request.HoleCount, request.LabelText(), notes)
            If screwFile <> "" Then chosenScrews.Add(request.Key, screwFile)
        Next
    End If
    Dim screwModels As New System.Collections.Generic.Dictionary(Of String, MGHWasherModel)(System.StringComparer.OrdinalIgnoreCase)
    stepName = "Reading the screw"
    Dim screwByFile As New System.Collections.Generic.Dictionary(Of String, MGHWasherModel)(System.StringComparer.OrdinalIgnoreCase)
    For Each lengthKey As String In New System.Collections.Generic.List(Of String)(chosenScrews.Keys)
        Dim screwPath As String = chosenScrews(lengthKey)
        If screwByFile.ContainsKey(screwPath) Then
            If screwByFile(screwPath) Is Nothing Then
                chosenScrews.Remove(lengthKey)
            Else
                screwModels.Add(lengthKey, screwByFile(screwPath))
            End If
            Continue For
        End If
        Try
            stepName = "Opening the screw"
            Dim screwModel As MGHWasherModel = MGHReadScrew(app, screwPath)
            stepName = "Choosing the screw mounting face"
            Dim lengthLabel As String = lengthKey
            Dim barAt As Integer = lengthKey.LastIndexOf("|"c)
            If barAt >= 0 AndAlso barAt < lengthKey.Length - 1 Then lengthLabel = lengthKey.Substring(barAt + 1) & " in " & lengthKey.Substring(0, barAt)
            If Not MGHUseMountingFace(app, asm, screwModel, lengthLabel & " screw", faceHint, notes, "screw") Then
                notes.Add(lengthLabel & " screw was skipped because its mounting face was not selected.")
                screwByFile.Add(screwPath, Nothing)
                chosenScrews.Remove(lengthKey)
            Else
                screwByFile.Add(screwPath, screwModel)
                screwModels.Add(lengthKey, screwModel)
            End If
        Catch ex As System.Exception
            notes.Add(lengthKey & " screw was not placed while " & stepName & ": " & ex.Message)
            screwByFile.Add(screwPath, Nothing)
            chosenScrews.Remove(lengthKey)
        End Try
    Next
    If washerModels.Count = 0 AndAlso nutModels.Count = 0 AndAlso screwModels.Count = 0 Then
        Return "Hardware was not placed." & vbCrLf & String.Join(vbCrLf, notes.ToArray())
    End If

    Dim washersPlaced As Integer = 0
    Dim nutsPlaced As Integer = 0
    Dim screwsPlaced As Integer = 0
    Dim replaced As Integer = 0
    stepName = "Placing hardware in the assembly"
    Dim placeSteps As Integer = 0
    For Each counted As OutputGroup In groups.Values
        If counted.Screw Is Nothing Then Continue For
        Dim countedSize As String = counted.Screw.Trim()
        Dim countedWasher As Boolean = washerModels.ContainsKey(countedSize)
        Dim countedNut As Boolean = nutModels.ContainsKey(countedSize)
        Dim countedWasherCm As Double = 0
        Dim countedNutCm As Double = 0
        If countedWasher Then countedWasherCm = washerModels(countedSize).Thickness
        If countedNut Then countedNutCm = nutModels(countedSize).Thickness
        Dim countedScrewWasher As Double = 0
        Dim countedNutWasher As Double = 0
        Dim countedNutIn As Double = 0
        MGHScrewAllowances(countedWasherCm, countedNutCm, placeUnderScrew, placeUnderNut, placeNut AndAlso countedNut, countedScrewWasher, countedNutWasher, countedNutIn)
        Dim countedIndex As Integer
        For countedIndex = 0 To counted.Centers.Count - 1
            If countedWasher AndAlso placeUnderScrew Then placeSteps += 1
            If countedWasher AndAlso placeUnderNut Then placeSteps += 1
            If countedNut AndAlso placeNut Then placeSteps += 1
            If placeScrew Then
                Dim countedRim As MGHComponentRim = Nothing
                If counted.Rims IsNot Nothing AndAlso countedIndex < counted.Rims.Count Then countedRim = counted.Rims(countedIndex)
                Dim countedGrip As Double = MGHHoleGripCm(app, plateOcc, plateToAssembly, counted.Centers(countedIndex), countedRim)
                Dim countedKey As String = MGHScrewLengthKey(countedSize, MGHScrewRequiredInches(countedGrip, countedScrewWasher, countedNutWasher, countedNutIn))
                If screwModels.ContainsKey(countedKey) Then placeSteps += 1
            End If
        Next
    Next
    If placeSteps < 1 Then placeSteps = 1
    Try
        hardwareProgress = app.CreateProgressBar(False, placeSteps, "Grouped Mounting Hardware - Placing Hardware")
    Catch
        hardwareProgress = Nothing
    End Try
    Dim placeIndex As Integer = 0
    Dim tg As Inventor.TransientGeometry = app.TransientGeometry
    Dim seatCache As New System.Collections.Generic.Dictionary(Of String, MGHSeatCacheEntry)(System.StringComparer.Ordinal)
    Dim knownHardware As System.Collections.Generic.List(Of MGHKnownHardware) = MGHListExistingHardware(app, asm)
    MGHBeginDeferredAssembly(app, previousDefer, deferArmed)
        For Each g As OutputGroup In groups.Values
            If g.Screw Is Nothing Then Continue For
            Dim sizeName As String = g.Screw.Trim()
            Dim washerModel As MGHWasherModel = Nothing
            Dim nutModel As MGHWasherModel = Nothing
            If washerModels.ContainsKey(sizeName) Then washerModel = washerModels(sizeName)
            If nutModels.ContainsKey(sizeName) Then nutModel = nutModels(sizeName)
            Dim sizeHasScrew As Boolean = False
            If placeScrew Then
                For Each lengthKey As String In screwModels.Keys
                    If lengthKey.StartsWith(sizeName & "|", System.StringComparison.OrdinalIgnoreCase) Then
                        sizeHasScrew = True
                        Exit For
                    End If
                Next
            End If
            If washerModel Is Nothing AndAlso nutModel Is Nothing AndAlso Not sizeHasScrew Then Continue For
            Dim groupWasherCm As Double = 0
            Dim groupNutCm As Double = 0
            If washerModel IsNot Nothing Then groupWasherCm = washerModel.Thickness
            If nutModel IsNot Nothing Then groupNutCm = nutModel.Thickness
            Dim groupScrewWasher As Double = 0
            Dim groupNutWasher As Double = 0
            Dim groupNutIn As Double = 0
            MGHScrewAllowances(groupWasherCm, groupNutCm, placeUnderScrew, placeUnderNut, placeNut AndAlso nutModel IsNot Nothing, groupScrewWasher, groupNutWasher, groupNutIn)
            Dim centerIndex As Integer
            For centerIndex = 0 To g.Centers.Count - 1
                Dim center As Inventor.Point = g.Centers(centerIndex)
                Dim rim As MGHComponentRim = Nothing
                If g.Rims IsNot Nothing AndAlso centerIndex < g.Rims.Count Then rim = g.Rims(centerIndex)
                Dim nutWasherThickness As Double = 0
                Dim nutWasherPlaced As Boolean = False
                Dim screwWasherThickness As Double = 0
                Dim screwWasherPlaced As Boolean = False
                Dim roleIndex As Integer
                For roleIndex = 0 To 1
                    Dim underNut As Boolean = (roleIndex = 1)
                    If washerModel Is Nothing Then Continue For
                    If underNut AndAlso Not placeUnderNut Then Continue For
                    If Not underNut AndAlso Not placeUnderScrew Then Continue For
                    placeIndex += 1
                    MGHProgressTick(hardwareProgress, app, "Placing " & sizeName & " " & If(underNut, "washer under nut", "washer under screw") & " (" & placeIndex.ToString() & " of " & placeSteps.ToString() & ")")
                    Dim onSelectedRim As Boolean = MGHWasherUsesSelectedRim(underNut, nutOnSelectedRim)
                    Dim endName As String = If(onSelectedRim, "Selected", "Opposite")
                    Dim roleLabel As String = If(underNut, "washer under nut", "washer under screw")
                    Dim contact As Inventor.Point = Nothing
                    Dim outwardAsm As Inventor.UnitVector = Nothing
                    Dim holeEdge As Inventor.Edge = Nothing
                    Dim seated As Boolean = False
                    If onSelectedRim Then
                        If rim Is Nothing Then
                            notes.Add(sizeName & " " & roleLabel & " at " & MGHFormatPoint(center) & " was skipped because the component hole rim was not recorded.")
                            Continue For
                        End If
                        seated = MGHComponentWasherSeat(app, rim, True, contact, outwardAsm, holeEdge, seatCache)
                    Else
                        seated = MGHPlateHardwareSeat(app, plateOcc, plateToAssembly, plateOutX, plateOutY, plateOutZ, center, contact, outwardAsm, holeEdge)
                    End If
                    If Not seated Then
                        notes.Add(sizeName & " " & roleLabel & " at " & MGHFormatPoint(center) & " was skipped because its seat face was not found.")
                        Continue For
                    End If
                    Dim added As Integer = MGHPlaceHardwareItem(app, asm, washerModel, contact, outwardAsm, _
                        "Washer", sizeName, center, endName, If(underNut, "UnderNut", "UnderScrew"), _
                        chosenWashers(sizeName), roleLabel, knownHardware, notes, replaced)
                    washersPlaced += added
                    If underNut AndAlso added = 1 Then
                        nutWasherPlaced = True
                        nutWasherThickness = washerModel.Thickness
                    End If
                    If Not underNut AndAlso added = 1 Then
                        screwWasherPlaced = True
                        screwWasherThickness = washerModel.Thickness
                    End If
                Next
                If placeNut AndAlso nutModel IsNot Nothing Then
                    placeIndex += 1
                    MGHProgressTick(hardwareProgress, app, "Placing " & sizeName & " nut (" & placeIndex.ToString() & " of " & placeSteps.ToString() & ")")
                    Dim nutOnRim As Boolean = MGHWasherUsesSelectedRim(True, nutOnSelectedRim)
                    Dim nutEnd As String = If(nutOnRim, "Selected", "Opposite")
                    Dim nutContact As Inventor.Point = Nothing
                    Dim nutOutward As Inventor.UnitVector = Nothing
                    Dim nutEdge As Inventor.Edge = Nothing
                    Dim nutSeated As Boolean = False
                    If nutOnRim Then
                        If rim Is Nothing Then
                            notes.Add(sizeName & " nut at " & MGHFormatPoint(center) & " was skipped because the component hole rim was not recorded.")
                            nutSeated = False
                        Else
                            nutSeated = MGHComponentWasherSeat(app, rim, True, nutContact, nutOutward, nutEdge, seatCache)
                        End If
                    Else
                        nutSeated = MGHPlateHardwareSeat(app, plateOcc, plateToAssembly, plateOutX, plateOutY, plateOutZ, center, nutContact, nutOutward, nutEdge)
                    End If
                    If Not nutSeated Then
                        If rim IsNot Nothing OrElse nutOnRim Then
                            If Not nutOnRim OrElse rim IsNot Nothing Then notes.Add(sizeName & " nut at " & MGHFormatPoint(center) & " was skipped because its seat face was not found.")
                        End If
                    Else
                        Dim stackOnWasher As Boolean = nutWasherPlaced AndAlso nutWasherThickness > 0.000000001
                        If stackOnWasher Then
                            Dim stackedX As Double, stackedY As Double, stackedZ As Double
                            MGHOffsetPoint(nutContact.X, nutContact.Y, nutContact.Z, nutOutward.X, nutOutward.Y, nutOutward.Z, _
                                nutWasherThickness, stackedX, stackedY, stackedZ)
                            nutContact = tg.CreatePoint(stackedX, stackedY, stackedZ)
                        End If
                        nutsPlaced += MGHPlaceHardwareItem(app, asm, nutModel, nutContact, nutOutward, _
                            "Nut", sizeName, center, nutEnd, "Nut", chosenNuts(sizeName), "nut", knownHardware, notes, replaced)
                    End If
                End If
                Dim screwKey As String = MGHScrewLengthKey(sizeName, MGHScrewRequiredInches(MGHHoleGripCm(app, plateOcc, plateToAssembly, center, rim), groupScrewWasher, groupNutWasher, groupNutIn))
                Dim screwModel As MGHWasherModel = Nothing
                If screwModels.ContainsKey(screwKey) Then screwModel = screwModels(screwKey)
                If placeScrew AndAlso screwModel IsNot Nothing Then
                    placeIndex += 1
                    MGHProgressTick(hardwareProgress, app, "Placing " & sizeName & " " & screwKey.Substring(screwKey.LastIndexOf("|"c) + 1) & " in screw (" & placeIndex.ToString() & " of " & placeSteps.ToString() & ")")
                    Dim screwOnRim As Boolean = MGHWasherUsesSelectedRim(False, nutOnSelectedRim)
                    Dim screwEnd As String = If(screwOnRim, "Selected", "Opposite")
                    Dim screwContact As Inventor.Point = Nothing
                    Dim screwOutward As Inventor.UnitVector = Nothing
                    Dim screwEdge As Inventor.Edge = Nothing
                    Dim screwSeated As Boolean = False
                    If screwOnRim Then
                        If rim Is Nothing Then
                            notes.Add(sizeName & " screw at " & MGHFormatPoint(center) & " was skipped because the component hole rim was not recorded.")
                        Else
                            screwSeated = MGHComponentWasherSeat(app, rim, True, screwContact, screwOutward, screwEdge, seatCache)
                        End If
                    Else
                        screwSeated = MGHPlateHardwareSeat(app, plateOcc, plateToAssembly, plateOutX, plateOutY, plateOutZ, center, screwContact, screwOutward, screwEdge)
                    End If
                    If screwSeated Then
                        Dim stackOnWasher As Boolean = screwWasherPlaced AndAlso screwWasherThickness > 0.000000001
                        If stackOnWasher Then
                            Dim stackedX As Double, stackedY As Double, stackedZ As Double
                            MGHOffsetPoint(screwContact.X, screwContact.Y, screwContact.Z, screwOutward.X, screwOutward.Y, screwOutward.Z, _
                                screwWasherThickness, stackedX, stackedY, stackedZ)
                            screwContact = tg.CreatePoint(stackedX, stackedY, stackedZ)
                        End If
                        screwsPlaced += MGHPlaceHardwareItem(app, asm, screwModel, screwContact, screwOutward, _
                            "Screw", sizeName, center, screwEnd, "Screw", chosenScrews(screwKey), "screw", knownHardware, notes, replaced)
                    ElseIf rim IsNot Nothing OrElse Not screwOnRim Then
                        notes.Add(sizeName & " screw at " & MGHFormatPoint(center) & " was skipped because its seat face was not found.")
                    End If
                End If
            Next
        Next
    If deferArmed Then MGHProgressMessage(hardwareProgress, app, "Updating the assembly once")
    MGHEndDeferredAssembly(app, asm, deferArmed, previousDefer)
    app.StatusBarText = ""

    Dim summary As New System.Text.StringBuilder()
    summary.Append("Washers placed: " & washersPlaced.ToString())
    If placeNut Then summary.Append(vbCrLf & "Nuts placed: " & nutsPlaced.ToString())
    If placeScrew Then summary.Append(vbCrLf & "Screws placed: " & screwsPlaced.ToString())
    If replaced > 0 Then summary.Append(vbCrLf & "Previous hardware replaced: " & replaced.ToString())
    If notes.Count > 0 Then
        summary.Append(vbCrLf & "Hardware notes:")
        For Each noteText As String In notes
            summary.Append(vbCrLf & "- " & noteText)
        Next
    End If
    If hardwareProgress IsNot Nothing Then
        Try
            hardwareProgress.Close()
        Catch
        End Try
        hardwareProgress = Nothing
    End If
    Return summary.ToString()
    Catch ex As System.Exception
        If hardwareProgress IsNot Nothing Then
            Try
                hardwareProgress.Close()
            Catch
            End Try
        End If
        MGHEndDeferredAssembly(app, asm, deferArmed, previousDefer)
        Return "Hardware was not placed during " & stepName & "." & vbCrLf & ex.Message
    End Try
End Function

' AssemblyOptions.DeferUpdate is the application option that pauses assembly solves.
' Part and sheet-metal definitions do not have DeferUpdates. Always restore the previous value.
Sub MGHBeginDeferredAssembly(app As Inventor.Application, ByRef previousDefer As Boolean, ByRef armed As Boolean)
    armed = False
    previousDefer = False
    If app Is Nothing Then Return
    Try
        previousDefer = app.AssemblyOptions.DeferUpdate
        If previousDefer Then Return
        app.AssemblyOptions.DeferUpdate = True
        armed = True
    Catch
        armed = False
    End Try
End Sub

Sub MGHEndDeferredAssembly(app As Inventor.Application, asm As Inventor.AssemblyDocument, _
    ByRef armed As Boolean, previousDefer As Boolean)
    If Not armed Then Return
    armed = False
    Try
        If app IsNot Nothing Then app.AssemblyOptions.DeferUpdate = previousDefer
    Catch
    End Try
    Try
        If asm IsNot Nothing AndAlso asm.RequiresUpdate Then asm.Update2(True)
    Catch
    End Try
End Sub


Function MGHDefaultThread(size As String) As String
    Select Case size
        Case "#0" : Return "0-80 UNF"
        Case "#1" : Return "1-64 UNC"
        Case "#2" : Return "2-56 UNC"
        Case "#3" : Return "3-48 UNC"
        Case "#4" : Return "4-40 UNC"
        Case "#5" : Return "5-40 UNC"
        Case "#6" : Return "6-32 UNC"
        Case "#7" : Return "7-32 UNC"
        Case "#8" : Return "8-32 UNC"
        Case "#9" : Return "9-24 UNC"
        Case "#10" : Return "10-24 UNC"
        Case "#11" : Return "11-24 UNC"
        Case "#12" : Return "12-24 UNC"
        Case "1/4" : Return "1/4-20 UNC"
        Case Else : Return ""
    End Select
End Function

Function MGHThreadNominalFromDesignation(designation As String) As Double
    Dim textValue As String=designation.Trim().ToUpperInvariant().Replace("#", "")
    If textValue.StartsWith("M") Then
        Dim token As String=textValue.Substring(1).Split("X"c)(0)
        Dim mm As Double=0
        If Double.TryParse(token,System.Globalization.NumberStyles.Float,System.Globalization.CultureInfo.InvariantCulture,mm) Then Return mm/25.4
    Else
        Dim token As String=textValue.Split("-"c)(0)
        If token.Contains("/") Then
            Dim fraction As String()=token.Split("/"c)
            Dim numerator As Double=0, denominator As Double=0
            If fraction.Length=2 AndAlso _
               Double.TryParse(fraction(0),System.Globalization.NumberStyles.Float,System.Globalization.CultureInfo.InvariantCulture,numerator) AndAlso _
               Double.TryParse(fraction(1),System.Globalization.NumberStyles.Float,System.Globalization.CultureInfo.InvariantCulture,denominator) AndAlso denominator>0 Then
                Return numerator/denominator
            End If
        Else
            Dim gauge As Integer=0
            If Integer.TryParse(token,gauge) AndAlso gauge>=0 AndAlso gauge<=12 Then
                Return 0.060+0.013*gauge
            End If
        End If
    End If
    Return 0.0
End Function

Function MGHThreadNominalDiameter(size As String) As Double
    Select Case size
        Case "#0": Return 0.060
        Case "#1": Return 0.073
        Case "#2": Return 0.086
        Case "#3": Return 0.099
        Case "#4": Return 0.112
        Case "#5": Return 0.125
        Case "#6": Return 0.138
        Case "#7": Return 0.151
        Case "#8": Return 0.164
        Case "#9": Return 0.177
        Case "#10": Return 0.190
        Case "#11": Return 0.203
        Case "#12": Return 0.216
        Case "1/4": Return 0.250
    End Select
    Return 0
End Function

Function MGHFitEnum(fit As String) As Inventor.FastenerFitType
    Select Case fit
        Case "Close" : Return Inventor.FastenerFitType.kCloseFitType
        Case "Loose" : Return Inventor.FastenerFitType.kLooseFitType
        Case Else : Return Inventor.FastenerFitType.kNormalFitType
    End Select
End Function

Sub MGHApplyClearanceInfo(holes As Inventor.HoleFeatures,h As Inventor.HoleFeature,g As OutputGroup)
    Try
        Dim ci As Inventor.HoleClearanceInfo=holes.CreateClearanceInfo(g.ClearanceStandard,g.ClearanceFamily,g.Screw,MGHFitEnum(g.Fit))
        h.ClearanceInfo=ci
        If Not h.IsClearanceHole Then Throw New System.Exception("Inventor did not mark it as a clearance hole.")
    Catch ex As System.Exception
        Throw New System.Exception("Native clearance could not be resolved from the installed Clearance.xls: " & g.Screw & " " & g.Fit & ". " & _
            "Switch this row to Custom/Press-Fit if an exact diameter-only hole is required. Details: " & ex.Message)
    End Try
End Sub

Function MGHCreateGroupedFeature(holes As Inventor.HoleFeatures,place As Inventor.SketchHolePlacementDefinition, _
    g As OutputGroup,direction As Inventor.PartFeatureExtentDirectionEnum) As Inventor.HoleFeature
    Dim diaInfo As Object=Nothing
    If g.Mode="Threaded" Then
        Try
            diaInfo=holes.CreateTapInfo(True,g.ThreadType,g.ThreadDesignation,g.ThreadClass,True)
        Catch ex As System.Exception
            Throw New System.Exception("Thread spec not found in local Thread.xls for " & g.Label & _
                ": " & g.ThreadType & " / " & g.ThreadDesignation & " / " & g.ThreadClass & ". " & ex.Message)
        End Try
    Else
        diaInfo=g.DiameterIn.ToString("0.000000",System.Globalization.CultureInfo.InvariantCulture) & " in"
    End If
    Dim h As Inventor.HoleFeature=Nothing
    Dim seatDia As String=g.SeatDiameterIn.ToString("0.000000",System.Globalization.CultureInfo.InvariantCulture) & " in"
    Select Case g.Seat
        Case "None"
            h=holes.AddDrilledByThroughAllExtent(place,diaInfo,direction)
        Case "Counterbore"
            h=holes.AddCBoreByThroughAllExtent(place,diaInfo,direction,seatDia, _
                g.SeatDepthIn.ToString("0.000000",System.Globalization.CultureInfo.InvariantCulture) & " in")
        Case "Countersink"
            h=holes.AddCSinkByThroughAllExtent(place,diaInfo,direction,seatDia, _
                g.SeatAngleDeg.ToString("0.0000",System.Globalization.CultureInfo.InvariantCulture) & " deg")
        Case "Spotface"
            h=holes.AddSpotFaceByThroughAllExtent(place,diaInfo,direction,seatDia, _
                g.SeatDepthIn.ToString("0.000000",System.Globalization.CultureInfo.InvariantCulture) & " in")
        Case Else
            Throw New System.Exception("Unrecognized seat: " & g.Seat)
    End Select
    If h Is Nothing Then Throw New System.Exception("Inventor did not return a hole feature for " & g.Label)
    ' Plain drilled clearance holes use the local table. A countersink, counterbore,
    ' or spotface keeps the diameters from the review. Linking those seats to
    ' Clearance.xls makes Inventor re-read the spreadsheet on every edit, which
    ' takes minutes even for two or three holes.
    If MGHLinkClearanceTable(g.Mode, g.Seat) Then MGHApplyClearanceInfo(holes,h,g)
    Return h
End Function


' Inventor may replace user-entered seat dimensions when ClearanceInfo is applied.
' Make explicit dimensions authoritative. Inventor API works in cm and radians;
' using unit-qualified expressions avoids locale/document-unit ambiguity.
Sub MGHEnforceCountersink(h As Inventor.HoleFeature,g As OutputGroup)
    If g.Seat<>"Countersink" Then Return
    If h.HoleType<>Inventor.HoleTypeEnum.kCounterSinkHole Then
        Throw New System.Exception("Feature is not a countersink: " & g.Label)
    End If
    Try
        Dim desiredDiameterCm As Double = g.SeatDiameterIn * 2.54
        Dim desiredAngleRad As Double = g.SeatAngleDeg * System.Math.PI / 180.0
        If h.CSinkDiameter Is Nothing OrElse h.CSinkAngle Is Nothing Then
            Throw New System.Exception("Inventor did not expose countersink size parameters.")
        End If
        If System.Math.Abs(h.CSinkDiameter.ModelValue-desiredDiameterCm)>0.00002 Then
            h.CSinkDiameter.Expression = g.SeatDiameterIn.ToString("0.000000", _
                System.Globalization.CultureInfo.InvariantCulture) & " in"
        End If
        If System.Math.Abs(h.CSinkAngle.ModelValue-desiredAngleRad)>0.00001 Then
            h.CSinkAngle.Expression = g.SeatAngleDeg.ToString("0.0000", _
                System.Globalization.CultureInfo.InvariantCulture) & " deg"
        End If
    Catch ex As System.Exception
        Throw New System.Exception("Inventor would not retain the requested countersink dimensions for '" & _
            g.Label & "'. The local clearance table may lock the seat dimensions. " & _
            "Try hole type Custom/Press-Fit for exact, dimension-driven geometry. " & _
            "The transaction will be rolled back; no incorrect countersink is accepted. Details: " & ex.Message, ex)
    End Try
    MGHAssertCountersink(h,g)
End Sub

' Must be used AFTER final document recompute, not just immediately after creation.
Sub MGHAssertCountersink(h As Inventor.HoleFeature,g As OutputGroup)
    If g.Seat<>"Countersink" Then Return
    If h.HoleType<>Inventor.HoleTypeEnum.kCounterSinkHole Then
        Throw New System.Exception("Countersink type changed unexpectedly: " & g.Label)
    End If
    Dim actualDia As Double = h.CSinkDiameter.ModelValue / 2.54
    Dim actualDeg As Double = h.CSinkAngle.ModelValue * 180.0 / System.Math.PI
    If System.Math.Abs(actualDia-g.SeatDiameterIn)>0.00001 OrElse _
       System.Math.Abs(actualDeg-g.SeatAngleDeg)>0.001 Then
        Throw New System.Exception("Countersink size mismatch for '" & g.Label & "': requested Ø" & _
            g.SeatDiameterIn.ToString("0.0000",System.Globalization.CultureInfo.InvariantCulture) & _
            " in × " & g.SeatAngleDeg.ToString("0.#",System.Globalization.CultureInfo.InvariantCulture) & _
            "°, but Inventor holds Ø" & actualDia.ToString("0.0000",System.Globalization.CultureInfo.InvariantCulture) & _
            " in × " & actualDeg.ToString("0.###",System.Globalization.CultureInfo.InvariantCulture) & _
            "°. Transaction will be rolled back rather than retaining wrong geometry.")
    End If
End Sub

Sub MGHCheckExistingSeat(h As Inventor.HoleFeature,g As OutputGroup)
    Select Case g.Seat
        Case "None"
            If h.HoleType <> Inventor.HoleTypeEnum.kDrilledHole Then Throw New System.Exception("Existing feature seat changed: " & h.Name)
        Case "Counterbore"
            If h.HoleType <> Inventor.HoleTypeEnum.kCounterBoreHole Then Throw New System.Exception("Existing feature seat changed: " & h.Name)
            If System.Math.Abs(h.CBoreDiameter.Value-g.SeatDiameterIn*2.54)>0.0002 OrElse _
               System.Math.Abs(h.CBoreDepth.Value-g.SeatDepthIn*2.54)>0.0002 Then Throw New System.Exception("Counterbore dimensions changed: " & h.Name)
        Case "Countersink"
            If h.HoleType <> Inventor.HoleTypeEnum.kCounterSinkHole Then Throw New System.Exception("Existing feature seat changed: " & h.Name)
            If System.Math.Abs(h.CSinkDiameter.Value-g.SeatDiameterIn*2.54)>0.0002 OrElse _
               System.Math.Abs(h.CSinkAngle.Value-g.SeatAngleDeg*System.Math.PI/180.0)>0.0001 Then Throw New System.Exception("Countersink dimensions changed: " & h.Name)
        Case "Spotface"
            If h.HoleType <> Inventor.HoleTypeEnum.kSpotFaceHole Then Throw New System.Exception("Existing feature seat changed: " & h.Name)
            If System.Math.Abs(h.SpotFaceDiameter.Value-g.SeatDiameterIn*2.54)>0.0002 OrElse _
               System.Math.Abs(h.SpotFaceDepth.Value-g.SeatDepthIn*2.54)>0.0002 Then Throw New System.Exception("Spotface dimensions changed: " & h.Name)
    End Select
End Sub

' True when the point misses the plate face and a circular rim is centered on it.
' distance and rim gap are centimeters. A negative rim gap means no circular edge was found.
Function MGHAcceptExistingOpening(distanceToFaceCm As Double, nearestRimCenterCm As Double) As Boolean
    If distanceToFaceCm <= 0.003 Then Return False
    If nearestRimCenterCm < 0 Then Return False
    Return nearestRimCenterCm <= 0.08
End Function

' Plain clearance holes follow Clearance.xls. Seated holes keep the review diameters.
Function MGHLinkClearanceTable(mode As String, seat As String) As Boolean
    If mode Is Nothing OrElse seat Is Nothing Then Return False
    Return String.Equals(mode, "Clearance", System.StringComparison.OrdinalIgnoreCase) AndAlso _
           String.Equals(seat, "None", System.StringComparison.OrdinalIgnoreCase)
End Function

Function MGHNearestCircularCenterGap(face As Inventor.Face, point As Inventor.Point) As Double
    Dim best As Double = -1
    If face Is Nothing OrElse point Is Nothing Then Return -1
    Try
        For Each ed As Inventor.Edge In face.Edges
            Dim edgeCenter As Inventor.Point = Nothing
            Dim radius As Double = 0
            If Not MGHCircularEdge(ed, edgeCenter, radius) Then Continue For
            Dim gap As Double = edgeCenter.DistanceTo(point)
            If best < 0 OrElse gap < best Then best = gap
        Next
    Catch
    End Try
    Return best
End Function

Function MGHGroupUsesOpening(group As OutputGroup, point As Inventor.Point) As Boolean
    If group Is Nothing OrElse group.OpeningCenters Is Nothing OrElse point Is Nothing Then Return False
    For Each opening As Inventor.Point In group.OpeningCenters
        If opening IsNot Nothing AndAlso opening.DistanceTo(point) < 0.005 Then Return True
    Next
    Return False
End Function

Function MGHEdgeCenteredOn(edge As Inventor.Edge, point As Inventor.Point, toleranceCm As Double) As Boolean
    Dim edgeCenter As Inventor.Point = Nothing
    Dim radius As Double = 0
    If point Is Nothing OrElse Not MGHCircularEdge(edge, edgeCenter, radius) Then Return False
    Return edgeCenter.DistanceTo(point) <= toleranceCm
End Function

' The part has already been recomputed. Flip any hole that is still solid at its
' sample, then recompute once for the whole plate if any hole was flipped.
Function MGHConfirmCutDirections(doc As Inventor.PartDocument, def As Inventor.PartComponentDefinition, _
    groups As System.Collections.Generic.SortedDictionary(Of String, OutputGroup), _
    existing As System.Collections.Generic.Dictionary(Of String, Inventor.HoleFeature), _
    created As System.Collections.Generic.Dictionary(Of String, Inventor.HoleFeature), _
    samples As System.Collections.Generic.Dictionary(Of String, System.Collections.Generic.List(Of Inventor.Point)), _
    app As Inventor.Application, pb As Inventor.ProgressBar) As Integer
    Dim flipped As Integer = 0
    Dim pending As New System.Collections.Generic.List(Of String)()
    For Each g As OutputGroup In groups.Values
        If g Is Nothing OrElse Not samples.ContainsKey(g.Key) Then Continue For
        Dim feat As Inventor.HoleFeature = Nothing
        If created IsNot Nothing AndAlso created.ContainsKey(g.Key) Then
            feat = created(g.Key)
        ElseIf existing IsNot Nothing AndAlso existing.ContainsKey(g.Key) Then
            feat = existing(g.Key)
        End If
        If feat Is Nothing Then Continue For
        If Not MGHStillSolid(def, samples(g.Key)) Then Continue For
        MGHProgressMessage(pb, app, "First direction missed material - reversing " & g.Label)
        Dim currentExtent As Inventor.ThroughAllExtent = TryCast(feat.Extent, Inventor.ThroughAllExtent)
        If currentExtent Is Nothing Then Throw New System.Exception("Hole '" & g.Label & "' did not have a Through All extent.")
        feat.SetThroughAllExtent(MGHOppositeDirection(currentExtent.Direction))
        pending.Add(g.Key)
        flipped += 1
    Next
    If pending.Count = 0 Then Return 0
    If Not doc.Update2(False) Then
        Throw New System.Exception("Part update failed after reversing a hole cut direction.")
    End If
    For Each key As String In pending
        Dim label As String = key
        For Each g As OutputGroup In groups.Values
            If String.Equals(g.Key, key, System.StringComparison.Ordinal) Then
                label = g.Label
                Exit For
            End If
        Next
        If MGHStillSolid(def, samples(key)) Then
            Throw New System.Exception("Neither cut direction removed material at ALL selected positions for '" & _
                label & "'. Transaction will be aborted; inspect the selected plate face and geometry.")
        End If
    Next
    Return flipped
End Function

' Return the correct through-all direction by probing the actual solid on
' both sides of the SKETCH normal. Sketch normal, not face/camera normal,
' defines Inventor's positive-hole-extent direction.
Function DetermineInwardDirection(sk As Inventor.PlanarSketch, _
    body As Inventor.SurfaceBody, centers As System.Collections.Generic.List(Of Inventor.Point), _
    app As Inventor.Application) As Inventor.PartFeatureExtentDirectionEnum

    If body Is Nothing OrElse Not body.IsSolid Then
        Throw New System.Exception("Selected plate face does not belong to a solid body.")
    End If
    If centers Is Nothing OrElse centers.Count = 0 Then
        Throw New System.Exception("No new hole center is available to determine the cut direction.")
    End If

    ' Calculate a right-handed sketch normal using SketchToModelSpace.
    ' The model's assembly placement, face choice and camera have no effect.
    Dim t As Inventor.TransientGeometry = app.TransientGeometry
    Dim p0 As Inventor.Point = sk.SketchToModelSpace(t.CreatePoint2d(0, 0))
    Dim pX As Inventor.Point = sk.SketchToModelSpace(t.CreatePoint2d(1, 0))
    Dim pY As Inventor.Point = sk.SketchToModelSpace(t.CreatePoint2d(0, 1))
    Dim ax As Double = pX.X - p0.X
    Dim ay As Double = pX.Y - p0.Y
    Dim az As Double = pX.Z - p0.Z
    Dim bx As Double = pY.X - p0.X
    Dim by As Double = pY.Y - p0.Y
    Dim bz As Double = pY.Z - p0.Z
    Dim nx As Double = ay * bz - az * by
    Dim ny As Double = az * bx - ax * bz
    Dim nz As Double = ax * by - ay * bx
    Dim mag As Double = System.Math.Sqrt(nx * nx + ny * ny + nz * nz)
    If mag < 0.000000001 Then Throw New System.Exception("Could not calculate the sketch normal.")
    nx /= mag : ny /= mag : nz /= mag

    ' Units are cm (Inventor internal). These small tests accommodate thin plates.
    ' All candidates are evaluated before drilling, so a new location should
    ' have solid material immediately beneath the plate's mounting face.
    Dim offsets() As Double = {0.002, 0.005, 0.015, 0.03}
    For Each center As Inventor.Point In centers
        For Each offsetCm As Double In offsets
            Dim plus() As Double = {center.X + nx * offsetCm, center.Y + ny * offsetCm, center.Z + nz * offsetCm}
            Dim minus() As Double = {center.X - nx * offsetCm, center.Y - ny * offsetCm, center.Z - nz * offsetCm}
            Dim plusState As Inventor.ContainmentEnum = body.IsPointInside(plus, False)
            Dim minusState As Inventor.ContainmentEnum = body.IsPointInside(minus, False)
            If plusState = Inventor.ContainmentEnum.kInsideContainment AndAlso _
               minusState <> Inventor.ContainmentEnum.kInsideContainment Then
                Return Inventor.PartFeatureExtentDirectionEnum.kPositiveExtentDirection
            End If
            If minusState = Inventor.ContainmentEnum.kInsideContainment AndAlso _
               plusState <> Inventor.ContainmentEnum.kInsideContainment Then
                Return Inventor.PartFeatureExtentDirectionEnum.kNegativeExtentDirection
            End If
        Next
    Next
    Throw New System.Exception("Cannot determine which side of the selected sketch contains plate material. " & _
        "The locations may already be drilled, lie on a cutout, or the selected face may not be on a simple solid plate. " & _
        "No outward-directed holes will be created.")
End Function


' Show native Inventor progress, keeping the text descriptive even during a slow COM call.
' AllowCancel is intentionally false: stopping mid-feature while a transaction is
' in flight can leave inconsistent Inventor COM state. Normal errors abort the transaction.
Sub MGHProgressMessage(pb As Inventor.ProgressBar, app As Inventor.Application, message As String)
    If pb IsNot Nothing Then pb.Message = message
    app.StatusBarText = message
    app.UserInterfaceManager.DoEvents()
End Sub

Sub MGHProgressTick(pb As Inventor.ProgressBar, app As Inventor.Application, message As String)
    If pb IsNot Nothing Then
        pb.Message = message
        pb.UpdateProgress()
    End If
    app.StatusBarText = message
    app.UserInterfaceManager.DoEvents()
End Sub

' Work in centimeter model coordinates. Probe 0.02-0.30 mm beneath the plate
' plane at every specified center BEFORE the hole feature is created.
' These points must be inside material before cutting and outside afterward.
Function MGHFindInteriorSamples(sk As Inventor.PlanarSketch, body As Inventor.SurfaceBody, _
        centers As System.Collections.Generic.List(Of Inventor.Point), _
        app As Inventor.Application) As System.Collections.Generic.List(Of Inventor.Point)
    Dim t As Inventor.TransientGeometry = app.TransientGeometry
    Dim p0 As Inventor.Point = sk.SketchToModelSpace(t.CreatePoint2d(0, 0))
    Dim px As Inventor.Point = sk.SketchToModelSpace(t.CreatePoint2d(1, 0))
    Dim py As Inventor.Point = sk.SketchToModelSpace(t.CreatePoint2d(0, 1))
    Dim ux As Double = px.X - p0.X, uy As Double = px.Y - p0.Y, uz As Double = px.Z - p0.Z
    Dim vx As Double = py.X - p0.X, vy As Double = py.Y - p0.Y, vz As Double = py.Z - p0.Z
    Dim nx As Double = uy * vz - uz * vy
    Dim ny As Double = uz * vx - ux * vz
    Dim nz As Double = ux * vy - uy * vx
    Dim magnitude As Double = System.Math.Sqrt(nx * nx + ny * ny + nz * nz)
    If magnitude < 0.000000001 Then Throw New System.Exception("Could not calculate sketch normal for material verification.")
    nx /= magnitude : ny /= magnitude : nz /= magnitude
    Dim distances() As Double = {0.002, 0.005, 0.015, 0.03}
    Dim result As New System.Collections.Generic.List(Of Inventor.Point)()
    For Each center As Inventor.Point In centers
        Dim found As Boolean = False
        For Each offsetCm As Double In distances
            Dim plusArray() As Double = {center.X + nx * offsetCm, center.Y + ny * offsetCm, center.Z + nz * offsetCm}
            Dim minusArray() As Double = {center.X - nx * offsetCm, center.Y - ny * offsetCm, center.Z - nz * offsetCm}
            Dim plusInside As Boolean = (body.IsPointInside(plusArray, False) = Inventor.ContainmentEnum.kInsideContainment)
            Dim minusInside As Boolean = (body.IsPointInside(minusArray, False) = Inventor.ContainmentEnum.kInsideContainment)
            If plusInside Xor minusInside Then
                If plusInside Then
                    result.Add(t.CreatePoint(plusArray(0), plusArray(1), plusArray(2)))
                Else
                    result.Add(t.CreatePoint(minusArray(0), minusArray(1), minusArray(2)))
                End If
                found = True
                Exit For
            End If
        Next
        If Not found Then
            Throw New System.Exception("Cannot locate plate material under mounting hole at (" & _
                center.X.ToString("0.000") & ", " & center.Y.ToString("0.000") & ", " & _
                center.Z.ToString("0.000") & ") cm. Check the plate face and any existing holes.")
        End If
    Next
    Return result
End Function

Function MGHStillSolid(def As Inventor.PartComponentDefinition, _
    probePoints As System.Collections.Generic.List(Of Inventor.Point)) As Boolean
    For Each point As Inventor.Point In probePoints
        Dim xyz() As Double = {point.X, point.Y, point.Z}
        For Each b As Inventor.SurfaceBody In def.SurfaceBodies
            If b.IsSolid Then
                If b.IsPointInside(xyz, False) = Inventor.ContainmentEnum.kInsideContainment Then
                    Return True
                End If
            End If
        Next
    Next
    Return False
End Function

Function MGHOppositeDirection(d As Inventor.PartFeatureExtentDirectionEnum) As Inventor.PartFeatureExtentDirectionEnum
    If d = Inventor.PartFeatureExtentDirectionEnum.kPositiveExtentDirection Then
        Return Inventor.PartFeatureExtentDirectionEnum.kNegativeExtentDirection
    ElseIf d = Inventor.PartFeatureExtentDirectionEnum.kNegativeExtentDirection Then
        Return Inventor.PartFeatureExtentDirectionEnum.kPositiveExtentDirection
    End If
    Throw New System.Exception("Hole cut direction was not positive or negative.")
End Function

' A successful HoleFeature call is NOT evidence that material was removed!
' Confirm every sampled center is empty after model recompute. If not,
' reverse the actual feature extent and check again; fail/rollback if still solid.
Function MGHVerifyCutAndFlip(h As Inventor.HoleFeature, doc As Inventor.PartDocument, _
    def As Inventor.PartComponentDefinition, _
    samples As System.Collections.Generic.List(Of Inventor.Point), _
    app As Inventor.Application, pb As Inventor.ProgressBar, groupLabel As String) As Boolean
    If Not doc.Update2(False) Then
        Throw New System.Exception("Part update failed while checking cut direction for '" & groupLabel & "'.")
    End If
    If Not MGHStillSolid(def, samples) Then Return False

    MGHProgressMessage(pb, app, "First direction missed material - reversing " & groupLabel)
    Dim currentExtent As Inventor.ThroughAllExtent = TryCast(h.Extent, Inventor.ThroughAllExtent)
    If currentExtent Is Nothing Then Throw New System.Exception("Hole '" & groupLabel & "' did not have a Through All extent.")
    h.SetThroughAllExtent(MGHOppositeDirection(currentExtent.Direction))
    If Not doc.Update2(False) Then
        Throw New System.Exception("Part update failed after reversing hole '" & groupLabel & "'.")
    End If
    If MGHStillSolid(def, samples) Then
        Throw New System.Exception("Neither cut direction removed material at ALL selected positions for '" & _
            groupLabel & "'. Transaction will be aborted; inspect the selected plate face and geometry.")
    End If
    Return True
End Function

' Sketch and feature names are not the identity of an MGH group; attributes are.
' Make visible names collision-resistant. A rename failure is not fatal.
Function UniqueSketchName(def As Inventor.PartComponentDefinition, requested As String, _
    ownSketch As Inventor.PlanarSketch) As String
    For n As Integer = 1 To 1000
        Dim candidate As String = If(n = 1, requested, requested & " (" & n.ToString() & ")")
        Dim exists As Boolean = False
        For Each sk As Inventor.PlanarSketch In def.Sketches
            If sk Is ownSketch Then Continue For
            If String.Equals(sk.Name, candidate, System.StringComparison.OrdinalIgnoreCase) Then
                exists = True
                Exit For
            End If
        Next
        If Not exists Then Return candidate
    Next
    Throw New System.Exception("Could not find an unused sketch name.")
End Function

Function UniqueHoleName(allHoles As Inventor.HoleFeatures, requested As String, _
    ownHole As Inventor.HoleFeature) As String
    For n As Integer = 1 To 1000
        Dim candidate As String = If(n = 1, requested, requested & " (" & n.ToString() & ")")
        Dim exists As Boolean = False
        For Each hf As Inventor.HoleFeature In allHoles
            If hf Is ownHole Then Continue For
            If String.Equals(hf.Name, candidate, System.StringComparison.OrdinalIgnoreCase) Then
                exists = True
                Exit For
            End If
        Next
        If Not exists Then Return candidate
    Next
    Throw New System.Exception("Could not find an unused Hole feature name.")
End Function

Function ProjectToPlane(p As Inventor.Point, pl As Inventor.Plane, app As Inventor.Application) As Inventor.Point
    Dim n As Inventor.UnitVector = pl.Normal
    Dim o As Inventor.Point = pl.RootPoint
    Dim dist As Double = (p.X - o.X) * n.X + (p.Y - o.Y) * n.Y + (p.Z - o.Z) * n.Z
    Return app.TransientGeometry.CreatePoint(p.X - dist * n.X, p.Y - dist * n.Y, p.Z - dist * n.Z)
End Function

Function StablePlaneKey(pl As Inventor.Plane) As String
    Dim n As Inventor.UnitVector = pl.Normal
    Dim nx As Double = n.X, ny As Double = n.Y, nz As Double = n.Z
    If System.Math.Abs(nx) > 0.000001 Then
        If nx < 0 Then nx = -nx : ny = -ny : nz = -nz
    ElseIf System.Math.Abs(ny) > 0.000001 Then
        If ny < 0 Then nx = -nx : ny = -ny : nz = -nz
    ElseIf nz < 0 Then
        nx = -nx : ny = -ny : nz = -nz
    End If
    Dim o As Inventor.Point = pl.RootPoint
    Dim dist As Double = nx * o.X + ny * o.Y + nz * o.Z
    Return "PLANE:" & FmtKey(nx) & "," & FmtKey(ny) & "," & FmtKey(nz) & "," & FmtKey(dist)
End Function

Function FmtKey(x As Double) As String
    Return x.ToString("0.00000", System.Globalization.CultureInfo.InvariantCulture)
End Function

Function CleanName(s As String) As String
    Dim r As String = s.Trim()
    For Each c As Char In New Char() {"/"c, "\"c, ":"c, "*"c, "?"c, "<"c, ">"c, "|"c, ChrW(34)}
        r = r.Replace(c, "-"c)
    Next
    If r.Length > 70 Then r = r.Substring(0, 70)
    Return r
End Function

Function GuessFastener(dIn As Double) As String
    ' Determine nearest NOMINAL screw size, then intentionally round odd
    ' screw numbers above #3 DOWN to the previous even size.
    ' This is only a default suggestion, not a hardware design validation.
    Dim sizes() As String = {"#0", "#1", "#2", "#3", "#4", "#5", "#6", "#7", "#8", "#9", "#10", "#11", "#12", "1/4"}
    Dim nominals() As Double = {0.060, 0.073, 0.086, 0.099, 0.112, 0.125, 0.138, 0.151, 0.164, 0.177, 0.190, 0.203, 0.216, 0.250}
    Dim best As String = sizes(0)
    Dim err As Double = Double.MaxValue
    For i As Integer = 0 To sizes.Length - 1
        Dim e As Double = System.Math.Abs(dIn - nominals(i))
        If e < err Then
            best = sizes(i)
            err = e
        End If
    Next
    Select Case best
        Case "#5" : Return "#4"
        Case "#7" : Return "#6"
        Case "#9" : Return "#8"
        Case "#11" : Return "#10"
    End Select
    Return best
End Function

Function PresetDiameter(size As String, fit As String) As Double
    ' Typical US inch clearance-hole suggestions. VERIFY the relevant standard/table.
    ' Format close, normal, loose in inches. Values are editable on the review form.
    Dim options As New System.Collections.Generic.Dictionary(Of String, Double())(System.StringComparer.OrdinalIgnoreCase)
    options.Add("#0", New Double() {0.063, 0.067, 0.070})
    options.Add("#1", New Double() {0.076, 0.081, 0.089})
    options.Add("#2", New Double() {0.089, 0.096, 0.106})
    options.Add("#3", New Double() {0.101, 0.110, 0.116})
    options.Add("#4", New Double() {0.116, 0.128, 0.144})
    options.Add("#5", New Double() {0.128, 0.136, 0.154})
    options.Add("#6", New Double() {0.144, 0.1495, 0.1695})
    options.Add("#7", New Double() {0.157, 0.164, 0.183})  ' Uncommon size: approximate editable starting point
    options.Add("#8", New Double() {0.1695, 0.177, 0.196})
    options.Add("#9", New Double() {0.183, 0.189, 0.209})  ' Uncommon size: approximate editable starting point
    options.Add("#10", New Double() {0.196, 0.201, 0.221})
    options.Add("#11", New Double() {0.209, 0.215, 0.236})  ' Uncommon size: approximate editable starting point
    options.Add("#12", New Double() {0.221, 0.228, 0.250})
    options.Add("1/4", New Double() {0.257, 0.266, 0.281})
    If Not options.ContainsKey(size) Then Return 0.0
    Select Case fit
        Case "Close" : Return options(size)(0)
        Case "Normal" : Return options(size)(1)
        Case "Loose" : Return options(size)(2)
        Case Else : Return options(size)(1)
    End Select
End Function

Public Class HoleReviewForm
    Inherits System.Windows.Forms.Form
    Private grd As System.Windows.Forms.DataGridView
    Private items As System.Collections.Generic.SortedDictionary(Of String, InputBucket)
    Private loading As Boolean = False
    Public SkipHoleCreation As Boolean = False

    ' Columns: 0 source, 1 qty, 2 screw, 3 mode, 4 fit, 5 Ø, 6 thread type,
    ' 7 designation, 8 class, 9 seat, 10 seat Ø, 11 depth/angle, 12 name,
    ' 13 clearance standard, 14 fastener type (names from local Clearance.xls).
    Public Sub New(buckets As System.Collections.Generic.SortedDictionary(Of String, InputBucket))
        MyBase.New()
        items = buckets
        Me.Width = 1510 : Me.Height = 660
        Me.StartPosition = System.Windows.Forms.FormStartPosition.CenterScreen
        Me.FormBorderStyle = System.Windows.Forms.FormBorderStyle.Sizable
        Dim heading As New System.Windows.Forms.Label()
        heading.Text = "One native Hole feature per complete specification. Clearance by default; Tapped and Custom/Press-Fit available."
        heading.Left = 12 : heading.Top = 10 : heading.Width = 1440 : heading.Height = 24
        heading.Anchor = System.Windows.Forms.AnchorStyles.Top Or System.Windows.Forms.AnchorStyles.Left Or System.Windows.Forms.AnchorStyles.Right
        Me.Controls.Add(heading)
        grd = New System.Windows.Forms.DataGridView()
        grd.Left = 12 : grd.Top = 40 : grd.Width = 1465 : grd.Height = 408
        grd.Anchor = System.Windows.Forms.AnchorStyles.Top Or System.Windows.Forms.AnchorStyles.Bottom Or System.Windows.Forms.AnchorStyles.Left Or System.Windows.Forms.AnchorStyles.Right
        grd.AllowUserToAddRows = False : grd.AllowUserToDeleteRows = False
        grd.RowHeadersVisible = False
        grd.AutoSizeRowsMode = System.Windows.Forms.DataGridViewAutoSizeRowsMode.None
        grd.SelectionMode = System.Windows.Forms.DataGridViewSelectionMode.CellSelect
        grd.Columns.Add(New System.Windows.Forms.DataGridViewTextBoxColumn() With {.Name="Source", .HeaderText="Source Ø (in)", .Width=90, .ReadOnly=True})
        grd.Columns.Add(New System.Windows.Forms.DataGridViewTextBoxColumn() With {.Name="Qty", .HeaderText="Qty", .Width=38, .ReadOnly=True})
        Dim sc As New System.Windows.Forms.DataGridViewComboBoxColumn()
        sc.Name="Screw" : sc.HeaderText="Fastener" : sc.Width=80
        sc.Items.AddRange(New Object() {"#0","#1","#2","#3","#4","#5","#6","#7","#8","#9","#10","#11","#12","1/4","Custom"})
        grd.Columns.Add(sc)
        Dim mc As New System.Windows.Forms.DataGridViewComboBoxColumn()
        mc.Name="Mode" : mc.HeaderText="Hole type" : mc.Width=102
        mc.Items.AddRange(New Object() {"Clearance","Threaded","Custom/Press-Fit"})
        grd.Columns.Add(mc)
        Dim fc As New System.Windows.Forms.DataGridViewComboBoxColumn()
        fc.Name="Fit" : fc.HeaderText="Fit" : fc.Width=80
        fc.Items.AddRange(New Object() {"Close","Normal","Loose","Custom","Press-Fit"})
        grd.Columns.Add(fc)
        grd.Columns.Add(New System.Windows.Forms.DataGridViewTextBoxColumn() With {.Name="Diameter", .HeaderText="Pilot Ø (in)", .Width=88})
        grd.Columns.Add(New System.Windows.Forms.DataGridViewTextBoxColumn() With {.Name="ThreadType", .HeaderText="Thread table (type)", .Width=175})
        grd.Columns.Add(New System.Windows.Forms.DataGridViewTextBoxColumn() With {.Name="ThreadDesignation", .HeaderText="Thread designation", .Width=123})
        grd.Columns.Add(New System.Windows.Forms.DataGridViewTextBoxColumn() With {.Name="ThreadClass", .HeaderText="Class", .Width=55})
        Dim seatCol As New System.Windows.Forms.DataGridViewComboBoxColumn()
        seatCol.Name="Seat" : seatCol.HeaderText="Seat" : seatCol.Width=95
        seatCol.Items.AddRange(New Object() {"None","Counterbore","Countersink","Spotface"})
        grd.Columns.Add(seatCol)
        grd.Columns.Add(New System.Windows.Forms.DataGridViewTextBoxColumn() With {.Name="SeatDiameter", .HeaderText="Seat Ø (in)", .Width=93})
        grd.Columns.Add(New System.Windows.Forms.DataGridViewTextBoxColumn() With {.Name="SeatDepthAngle", .HeaderText="Depth (in) / CS angle (°)", .Width=170})
        grd.Columns.Add(New System.Windows.Forms.DataGridViewTextBoxColumn() With {.Name="Group", .HeaderText="Group name", .Width=190})
        grd.Columns.Add(New System.Windows.Forms.DataGridViewTextBoxColumn() With {.Name="ClearanceStandard", .HeaderText="Clearance standard (table)", .Width=175})
        grd.Columns.Add(New System.Windows.Forms.DataGridViewTextBoxColumn() With {.Name="ClearanceFamily", .HeaderText="Clearance fastener family", .Width=240})
        Me.Controls.Add(grd)
        Dim note As New System.Windows.Forms.Label()
        note.Left=12 : note.Top=456 : note.Width=1465 : note.Height=104
        note.Anchor = System.Windows.Forms.AnchorStyles.Bottom Or System.Windows.Forms.AnchorStyles.Left Or System.Windows.Forms.AnchorStyles.Right
        note.Text = "Clearance uses local Inventor Clearance.xls (diameter preview is approximate); Threaded uses Thread.xls (pilot Ø determined by table). " & _
                    "For a custom/PEM hole choose Custom/Press-Fit and enter EXACT Ø. Seats: Counterbore/Spotface need Ø + depth; Countersink needs exact Ø and dropdown angle (82° default, 100° optional). For native clearance, edit the clearance-family column to match local table/head style. " & _
                    "Place hardware only skips hole creation and places washers, nuts, and screws on the holes you already selected. A hole already in the plate is kept and used for hardware."
        Me.Controls.Add(note)
        Dim hardwareOnly As New System.Windows.Forms.Button()
        hardwareOnly.Text = "Place hardware only" : hardwareOnly.Width = 170 : hardwareOnly.Left = 996 : hardwareOnly.Top = 568
        hardwareOnly.Anchor = System.Windows.Forms.AnchorStyles.Bottom Or System.Windows.Forms.AnchorStyles.Right
        AddHandler hardwareOnly.Click, AddressOf HardwareOnlyClick
        Me.Controls.Add(hardwareOnly)
        Dim ok As New System.Windows.Forms.Button()
        ok.Text="Generate holes" : ok.Width=150 : ok.Left=1310 : ok.Top=568
        ok.Anchor = System.Windows.Forms.AnchorStyles.Bottom Or System.Windows.Forms.AnchorStyles.Right
        AddHandler ok.Click, AddressOf AcceptClick
        Me.Controls.Add(ok)
        Dim cancel As New System.Windows.Forms.Button()
        cancel.Text="Cancel" : cancel.Width=100 : cancel.Left=1178 : cancel.Top=568
        cancel.Anchor= System.Windows.Forms.AnchorStyles.Bottom Or System.Windows.Forms.AnchorStyles.Right
        AddHandler cancel.Click, AddressOf CancelClick
        Me.Controls.Add(cancel)
        ' No Form.AcceptButton/CancelButton due to Inventor 2027 .NET reference regression.
        loading=True
        For Each b As InputBucket In buckets.Values
            grd.Rows.Add(b.SourceKey,b.Centers.Count.ToString(),b.Screw,b.Mode,b.Fit, _
                b.DiameterIn.ToString("0.0000",System.Globalization.CultureInfo.InvariantCulture), _
                b.ThreadType,b.ThreadDesignation,b.ThreadClass,b.Seat,"","",b.GroupLabel, _
                b.ClearanceStandard,b.ClearanceFamily)
        Next
        For Each row As System.Windows.Forms.DataGridViewRow In grd.Rows
            If Convert.ToString(row.Cells(9).Value)="Countersink" Then
                SetSeatInputCell(row)
            End If
        Next
        loading=False
        AddHandler grd.CellValueChanged, AddressOf CellChanged
        AddHandler grd.CurrentCellDirtyStateChanged, AddressOf CellDirty
        AddHandler grd.DataError, AddressOf GridDataError
    End Sub

    Private Function MGHDefaultThread(size As String) As String
    Select Case size
        Case "#0" : Return "0-80 UNF"
        Case "#1" : Return "1-64 UNC"
        Case "#2" : Return "2-56 UNC"
        Case "#3" : Return "3-48 UNC"
        Case "#4" : Return "4-40 UNC"
        Case "#5" : Return "5-40 UNC"
        Case "#6" : Return "6-32 UNC"
        Case "#7" : Return "7-32 UNC"
        Case "#8" : Return "8-32 UNC"
        Case "#9" : Return "9-24 UNC"
        Case "#10" : Return "10-24 UNC"
        Case "#11" : Return "11-24 UNC"
        Case "#12" : Return "12-24 UNC"
        Case "1/4" : Return "1/4-20 UNC"
        Case Else : Return ""
    End Select
    End Function


    ' DataGridView supports different cell editors in the same column.
    ' For a countersink use a dropdown; for other seats keep an editable depth.
    Private Sub SetSeatInputCell(row As System.Windows.Forms.DataGridViewRow)
        Dim selectedSeat As String=Convert.ToString(row.Cells(9).Value)
        If selectedSeat="Countersink" Then
            Dim oldValue As String=Convert.ToString(row.Cells(11).Value).Trim()
            Dim angleCell As New System.Windows.Forms.DataGridViewComboBoxCell()
            angleCell.Items.AddRange(New Object() {"82","100"})
            row.Cells(11)=angleCell
            If oldValue="100" Then
                row.Cells(11).Value="100"
            Else
                row.Cells(11).Value="82"
            End If
        Else
            If TypeOf row.Cells(11) Is System.Windows.Forms.DataGridViewComboBoxCell Then
                row.Cells(11)=New System.Windows.Forms.DataGridViewTextBoxCell()
            End If
            row.Cells(11).Value=""
        End If
    End Sub

    Private Sub GridDataError(sender As Object, e As System.Windows.Forms.DataGridViewDataErrorEventArgs)
        e.ThrowException=False
    End Sub

    Private Sub CellDirty(sender As Object, e As System.EventArgs)
        If grd.IsCurrentCellDirty Then grd.CommitEdit(System.Windows.Forms.DataGridViewDataErrorContexts.Commit)
    End Sub

    Private Sub CellChanged(sender As Object, e As System.Windows.Forms.DataGridViewCellEventArgs)
        If loading OrElse e.RowIndex<0 Then Return
        If e.ColumnIndex<>2 AndAlso e.ColumnIndex<>3 AndAlso e.ColumnIndex<>4 AndAlso _
           e.ColumnIndex<>9 AndAlso e.ColumnIndex<>11 Then Return
        loading=True
        Try
            Dim row As System.Windows.Forms.DataGridViewRow=grd.Rows(e.RowIndex)
            Dim sz As String=Convert.ToString(row.Cells(2).Value)
            Dim mode As String=Convert.ToString(row.Cells(3).Value)
            Dim fit As String=Convert.ToString(row.Cells(4).Value)
            ' Only a fastener / hole type / fit change can repopulate pilot Ø.
            ' Seat/angle edits must NOT overwrite a custom pilot diameter.
            If e.ColumnIndex=2 OrElse e.ColumnIndex=3 OrElse e.ColumnIndex=4 Then
                If e.ColumnIndex=2 Then row.Cells(7).Value=MGHDefaultThread(sz)
                If mode="Clearance" Then
                    If sz="Custom" OrElse fit="Custom" OrElse fit="Press-Fit" Then
                        row.Cells(3).Value="Custom/Press-Fit"
                        row.Cells(4).Value="Custom"
                        row.Cells(5).Value=""
                        row.Cells(12).Value="Custom hole - edit name"
                    Else
                        row.Cells(5).Value=PresetDiameter(sz,fit).ToString("0.0000",System.Globalization.CultureInfo.InvariantCulture)
                        row.Cells(12).Value="Hole " & sz & " - " & fit
                    End If
                ElseIf mode="Threaded" Then
                    row.Cells(4).Value="Custom"
                    row.Cells(5).Value="" ' table drives tap drill diameter
                    row.Cells(12).Value="Tapped " & Convert.ToString(row.Cells(7).Value)
                Else
                    row.Cells(4).Value="Custom"
                    If e.ColumnIndex=3 Then row.Cells(5).Value=""
                    row.Cells(12).Value="Custom / Press-Fit " & sz
                End If
            End If
            If e.ColumnIndex=9 Then
                ' Seat Ø is always explicit. The *included angle* is a choice,
                ' with the US 82-degree countersink as default (100 also offered).
                row.Cells(10).Value=""
                SetSeatInputCell(row)
                If Convert.ToString(row.Cells(9).Value)="Countersink" AndAlso _
                   Convert.ToString(row.Cells(14).Value)="Flat Head Machine Screw (100)" Then
                    row.Cells(14).Value="Flat Head Machine Screw (82)"
                End If
            End If
            If e.ColumnIndex=11 AndAlso Convert.ToString(row.Cells(9).Value)="Countersink" Then
                ' Synchronize the standard table's 82/100 flat-head family
                ' with the requested included angle. Custom hardware families
                ' are not modified automatically.
                Dim family As String=Convert.ToString(row.Cells(14).Value)
                If family="Flat Head Machine Screw (82)" OrElse _
                   family="Flat Head Machine Screw (100)" Then
                    row.Cells(14).Value="Flat Head Machine Screw (" & _
                        Convert.ToString(row.Cells(11).Value) & ")"
                End If
            End If
        Finally
            loading=False
        End Try
    End Sub

    Private Sub AcceptClick(sender As Object,e As System.EventArgs)
        CommitReview(False)
    End Sub

    Private Sub HardwareOnlyClick(sender As Object, e As System.EventArgs)
        CommitReview(True)
    End Sub

    Private Sub CommitReview(skipHoles As Boolean)
        Try
            grd.EndEdit()
            Dim idx As Integer=0
            For Each b As InputBucket In items.Values
                Dim row As System.Windows.Forms.DataGridViewRow=grd.Rows(idx)
                b.Screw=Convert.ToString(row.Cells(2).Value).Trim()
                b.Mode=Convert.ToString(row.Cells(3).Value).Trim()
                b.Fit=Convert.ToString(row.Cells(4).Value).Trim()
                b.GroupLabel=Convert.ToString(row.Cells(12).Value).Trim()
                b.ThreadType=Convert.ToString(row.Cells(6).Value).Trim()
                b.ThreadDesignation=Convert.ToString(row.Cells(7).Value).Trim()
                b.ThreadClass=Convert.ToString(row.Cells(8).Value).Trim()
                b.ClearanceStandard=Convert.ToString(row.Cells(13).Value).Trim()
                b.ClearanceFamily=Convert.ToString(row.Cells(14).Value).Trim()
                b.Seat=Convert.ToString(row.Cells(9).Value).Trim()
                If b.GroupLabel="" Then Throw New System.Exception("Enter a group name on row " & (idx+1).ToString())
                If b.Mode="Clearance" Then
                    If b.Screw="Custom" OrElse (b.Fit<>"Normal" AndAlso b.Fit<>"Close" AndAlso b.Fit<>"Loose") Then
                        Throw New System.Exception("Native clearance needs a known fastener and Close/Normal/Loose fit on row " & (idx+1).ToString())
                    End If
                    If b.ClearanceStandard="" OrElse b.ClearanceFamily="" Then
                        Throw New System.Exception("Enter clearance standard and fastener family on row " & (idx+1).ToString())
                    End If
                End If
                If b.Mode="Threaded" Then
                    If b.ThreadType="" OrElse b.ThreadDesignation="" OrElse b.ThreadClass="" Then
                        Throw New System.Exception("Provide thread table, designation and class on row " & (idx+1).ToString())
                    End If
                    b.DiameterIn=0
                Else
                    Dim raw As String=Convert.ToString(row.Cells(5).Value).Trim()
                    Dim diameter As Double=0
                    If Not Double.TryParse(raw,System.Globalization.NumberStyles.Float,System.Globalization.CultureInfo.InvariantCulture,diameter) OrElse diameter<=0.01 OrElse diameter>2 Then
                        Throw New System.Exception("Enter hole Ø in inches (0.01 to 2.0) on row " & (idx+1).ToString())
                    End If
                    If b.Mode="Clearance" AndAlso System.Math.Abs(diameter-PresetDiameter(b.Screw,b.Fit))>0.00005 Then
                        ' Explicit edit takes precedence over tabulated clearance sizing.
                        b.Mode="Custom/Press-Fit" : b.Fit="Custom"
                        If b.GroupLabel.StartsWith("Hole " & b.Screw & " - ") Then b.GroupLabel="Hole " & b.Screw & " - Custom"
                    End If
                    b.DiameterIn=diameter
                End If
                b.SeatDiameterIn=0 : b.SeatDepthIn=0 : b.SeatAngleDeg=0
                If b.Seat<>"None" Then
                    Dim diaText As String=Convert.ToString(row.Cells(10).Value).Trim()
                    If Not Double.TryParse(diaText,System.Globalization.NumberStyles.Float,System.Globalization.CultureInfo.InvariantCulture,b.SeatDiameterIn) OrElse b.SeatDiameterIn<=0 Then
                        Throw New System.Exception("Enter seat Ø in inches on row " & (idx+1).ToString())
                    End If
                    Dim sizeText As String=Convert.ToString(row.Cells(11).Value).Trim()
                    If b.Seat="Countersink" Then
                        If Not Double.TryParse(sizeText,System.Globalization.NumberStyles.Float,System.Globalization.CultureInfo.InvariantCulture,b.SeatAngleDeg) Then
                            Throw New System.Exception("Enter countersink included angle in degrees (e.g. 82) on row " & (idx+1).ToString())
                        End If
                    Else
                        If Not Double.TryParse(sizeText,System.Globalization.NumberStyles.Float,System.Globalization.CultureInfo.InvariantCulture,b.SeatDepthIn) Then
                            Throw New System.Exception("Enter seat depth in inches on row " & (idx+1).ToString())
                        End If
                    End If
                End If
                idx+=1
            Next
            SkipHoleCreation = skipHoles
            Me.DialogResult=System.Windows.Forms.DialogResult.OK : Me.Close()
        Catch ex As System.Exception
            System.Windows.Forms.MessageBox.Show(ex.Message,"Correct review grid")
        End Try
    End Sub

    Private Function PresetDiameter(size As String,fit As String) As Double
        Dim options As New System.Collections.Generic.Dictionary(Of String,Double())(System.StringComparer.OrdinalIgnoreCase)
        options.Add("#0",New Double(){0.063,0.067,0.070})
        options.Add("#1",New Double(){0.076,0.081,0.089})
        options.Add("#2",New Double(){0.089,0.096,0.106})
        options.Add("#3",New Double(){0.101,0.110,0.116})
        options.Add("#4",New Double(){0.116,0.128,0.144})
        options.Add("#5",New Double(){0.128,0.136,0.154})
        options.Add("#6",New Double(){0.144,0.1495,0.1695})
        options.Add("#7",New Double(){0.157,0.164,0.183})
        options.Add("#8",New Double(){0.1695,0.177,0.196})
        options.Add("#9",New Double(){0.183,0.189,0.209})
        options.Add("#10",New Double(){0.196,0.201,0.221})
        options.Add("#11",New Double(){0.209,0.215,0.236})
        options.Add("#12",New Double(){0.221,0.228,0.250})
        options.Add("1/4",New Double(){0.257,0.266,0.281})
        If Not options.ContainsKey(size) Then Return 0.0
        Select Case fit
            Case "Close" : Return options(size)(0)
            Case "Normal" : Return options(size)(1)
            Case "Loose" : Return options(size)(2)
            Case Else : Return options(size)(1)
        End Select
    End Function

    Private Sub CancelClick(sender As Object,e As System.EventArgs)
        Me.DialogResult=System.Windows.Forms.DialogResult.Cancel : Me.Close()
    End Sub
End Class
